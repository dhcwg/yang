module ietf-dhcpv6-options-rfc3319 {
  yang-version 1.1;
  namespace "urn:ietf:params:xml:ns:yang:ietf-dhcpv6-options-rfc3319";
  prefix "rfc3319";

  import ietf-dhcpv6-options-rfc8415 {
    prefix "rfc8415";
  }

  import ietf-inet-types {
    prefix inet;
  }

  organization "DHC WG";
  contact 
   "cuiyong@tsinghua.edu.cn
    wangh13@mails.tsinghua.edu.cn
    lh.sunlinh@gmail.com
    ian.farrer@telekom.de
    sladjana.zechlin@telekom.de
    hezihao9512@gmail.com";

  description "This YANG module contains DHCPv6 options defined in RFC3319 that
    can be used by DHCPv6 servers.";

  revision 2019-06-07 {
    description "Major reworking to only contain RFC8415 options. if-feature
      for each option removed. Removed groupings of features by device or
      combination of devices. Added ";
    reference "I-D: draft-ietf-dhc-dhcpv6-yang";
  }

  /*
   * Features
   */
  
  feature server {
    description "DHCPv6 server";
  }
  		
  /*
   * Groupings
   */
  
  augment "/rfc8415:test" {

    container sip-server-domain-name-list-option {
      if-feature "server";
      description "OPTION_SIP_SERVER_D (21) SIP Servers Domain Name List";
      reference "RFC3319: Dynamic Host Configuration Protocol
        (DHCPv6) Options for Session Initiation Protocol (SIP) Servers";
      leaf sip-serv-domain-name {
        type inet:domain-name;
        mandatory true;
        description "sip server domain name";
      }
    }

    container sip-server-address-list-option {
      if-feature "server";
      description "OPTION_SIP_SERVER_A (22) SIP Servers IPv6 Address List";
      reference "RFC3319: Dynamic Host Configuration Protocol (DHCPv6)
        Options for Session Initiation Protocol (SIP) Servers";
      list sip-server {
        key sip-serv-id;
        description "sip server info";
        leaf sip-serv-id {
          type uint8;
          mandatory true;
          description "sip server id";
        }
        leaf sip-serv-addr {
          type inet:ipv6-address;
          mandatory true;
          description "sip server addr";
        }
      }
    }
  }
}
