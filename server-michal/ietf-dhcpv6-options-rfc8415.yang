module ietf-dhcpv6-options-rfc8415 {
  yang-version 1.1;
  namespace "urn:ietf:params:xml:ns:yang:ietf-dhcpv6-options-rfc8415";
  prefix "rfc8415";

  import ietf-inet-types {
    prefix inet;
  }
  import ietf-dhcpv6-types {
    prefix dhcpv6-types;
  }
  import ietf-dhcpv6-server {
    prefix dhcpv6-server;
  }

  organization "DHC WG";
  contact
    "cuiyong@tsinghua.edu.cn
    wangh13@mails.tsinghua.edu.cn
    lh.sunlinh@gmail.com
    ian.farrer@telekom.de
    sladjana.zechlin@telekom.de
    hezihao9512@gmail.com";

  description "This YANG module contains DHCPv6 options defined in RFC8415 that
    can be used by DHCPv6 clients, relays and servers.";

  revision 2019-06-07 {
    description "Major reworking to only contain RFC8415 options. if-feature
      for each option removed. Removed groupings of features by device or
      combination of devices. Added ";
    reference "I-D: draft-ietf-dhc-dhcpv6-yang";
  }

  revision 2018-09-04 {
    description "";
    reference "I-D: draft-ietf-dhc-dhcpv6-yang";
  }

  revision 2018-03-04 {
    description "Resolved most issues on the DHC official
      github";
    reference "I-D: draft-ietf-dhc-dhcpv6-yang";
  }

  revision 2017-12-22 {
    description "Resolve most issues on Ian's github.";
    reference "I-D: draft-ietf-dhc-dhcpv6-yang";
  }

  revision 2017-11-24 {
    description "First version of the separated DHCPv6 options
      YANG model.";
    reference "I-D:draft-ietf-dhc-dhcpv6-yang";
  }

  /*
   * Features
   */

  feature server {
    description "DHCPv6 server";
  }

  feature relay {
    description "DHCPv6 relay";
  }

  feature client {
    description "DHCPv6 client";
  }

  /*
   * Groupings
   */

  augment "/dhcpv6-server:config/dhcpv6-server:option-sets/dhcpv6-server:option-set/dhcpv6-server:options" {
     container options {
      description "Contains definitions for DHCv6 options configured on the
          DHCPv6 server, relay or client.";

      container option-request-option {
        if-feature "client";
        description "OPTION_ORO (6) Option Request Option. A client MUST include
            an Option Request option in a Solicit, Request, Renew, Rebind, or
            Information-request message to inform the server about options the
            client wants the server to send to the client.";
        reference "RFC8415: Dynamic Host Configuration Protocol for
            IPv6 (DHCPv6)";
        /*list oro-option {
          key option-code;
          description "List of options that the client is requesting, identified
          by option code.";
          leaf-list option-code {
          type uint16 {
          must "17 | 21..24 | 27..36 | 39..42 ";
          }
          mandatory true;
          description "Option code being requested by the client";
          }*/
        leaf-list oro-option {
          description "List of options that the client is requesting, identified
              by option code";
          type uint16 {
            range "17 | 21..24 | 27..36 | 39..42 | 49..52 | 54..60 | 62..65 | 69..78";
          }
        }
      }
     }

     container preference-option {
       if-feature "server";
       description "OPTION_PREFERENCE (7) Preference Option";
       reference "RFC8415: Dynamic Host Configuration Protocol for
          IPv6 (DHCPv6)";
       leaf pref-value {
         type uint8;
         mandatory true;
         description "The preference value for the server in this message.
            A 1-octet unsigned integer.";
       }
     }

     container auth-option {
       if-feature "server or relay";
       description "OPTION_AUTH (11) Authentication Option";
       reference "RFC8415: Dynamic Host Configuration Protocol for IPv6 (DHCPv6)";
       leaf protocol {
         type uint8;
         mandatory true;
         description "The authentication protocol used in this Authentication option.";
       }
       leaf algorithm {
         type uint8;
         mandatory true;
         description "The algorithm used in the authentication protocol.";
       }
       leaf rdm {
         type uint8;
         mandatory true;
         description "The replay detection method used in this Authentication
            option.";
       }
       leaf replay-detection {
         type uint64;
         mandatory true;
         description "The replay detection information for the RDM.";
       }
       leaf auth-information {
         type string;
         mandatory true;
         description "The authentication information, as specified by the
            protocol and algorithm used in this Authentication option.";
       }
     }

     container server-unicast-option {
       if-feature "server";
       description "OPTION_UNICAST (12) Server Unicast Option";
       reference "RFC8415: Dynamic Host Configuration Protocol for IPv6 (DHCPv6)";
       leaf server-address {
         type inet:ipv6-address;
         mandatory true;
         description "The 128-bit address to which the client
            should send messages delivered using unicast.";
       }
     }

     container status-code-option {
       if-feature "client or server or relay";
       description "OPTION_STATUS_CODE (13) Status Code Option.";
       reference "RFC8415: Dynamic Host Configuration Protocol for IPv6
          (DHCPv6)";
       leaf status-code {
         type uint16;
         mandatory true;
         description "The numeric code for the status encoded in this option.
            See the Status Codes registry at <https://www.iana.org/assignments/
            dhcpv6-parameters> for the current list of status codes.";
       }
       leaf status-message {
         type string;
         mandatory true;
         description "A UTF-8 encoded [RFC3629] text string suitable for display
            to an end user. MUST NOT be null-terminated.";
       }
     }

     container rapid-commit-option {
       if-feature "server or client";
       //presence "Enable sending of this option";
       description "OPTION_RAPID_COMMIT (14) Rapid Commit Option. The presence
          node is used to enable the option.";
       reference "RFC8415: Dynamic Host Configuration Protocol for IPv6
          (DHCPv6)";
     }

     container user-class-option {
       if-feature "client";
       description "OPTION_USER_CLASS (15) User Class Option";
       reference "RFC8415: Dynamic Host Configuration Protocol
          for IPv6 (DHCPv6)";
       list user-class-data {
         key user-class-datum-id;
         min-elements 1;
         description "The user classes of which the client is a member.";
         leaf user-class-datum-id {
           type uint8;
           mandatory true;
           description "User class datum ID";
         }
         leaf user-class-datum {
           type string;
           mandatory true;
           description "Opaque field representing a User Class of which the
              client is a member.";
         }
       }
     }

     container vendor-class-option {
       if-feature "client";
       description "OPTION_VENDOR_CLASS (16) Vendor Class Option";
       reference "RFC8415: Dynamic Host Configuration Protocol
          for IPv6 (DHCPv6)";
       list vendor-class-option-instances {
         key enterprise-number;
         description "The vendor class option allows for multiple instances in
            a single message. Each list entry defines the contents of an instance
            of the option.";
         leaf enterprise-number {
           type uint32;
           mandatory true;
           description "The vendor’s registered Enterprise Number as maintained
              by IANA.";
         }
         list vendor-class {
           key vendor-class-datum-id;
           description "The vendor classes of which the client is a member.";
           leaf vendor-class-datum-id {
             type uint8;
             mandatory true;
             description "Vendor class datum ID";
           }
           leaf vendor-class-datum {
             type string;
             mandatory true;
             description "Opaque field representing a vendor class of which the
                client is a member.";
           }
         }
       }
     }

     container vendor-specific-information-option {
       if-feature "server or client";
       description "OPTION_VENDOR_OPTS (17) Vendor-specific Information Option";
       reference "RFC8415: Dynamic Host Configuration Protocol
          for IPv6 (DHCPv6)";
       list vendor-specific-information-option-instances {
         key enterprise-number;
         description "The vendor specific information option allows for multiple
            instances in a single message. Each list entry defines the contents of
            an instance of the option.";
         leaf enterprise-number {
           type uint32;
           mandatory true;
           description "The vendor’s registered Enterprise Number, as maintained
              by IANA.";
         }
         list vendor-option-data {
           key sub-option-code;
           description "Vendor options, interpreted by vendor-specific client/
              server functions.";
           leaf sub-option-code {
             type uint16;
             mandatory true;
             description "The code for the sub-option.";
           }
           leaf sub-option-data {
             type string;
             mandatory true;
             description "The data area for the sub-option.";
           }
         }
       }
     }

     container interface-id-option {
       if-feature "relay";
       description "OPTION_INTERFACE_ID (18) Interface-Id Option";
       reference "RFC8415: Dynamic Host Configuration Protocol for
          IPv6 (DHCPv6)";
       leaf interface-id {
         type string;
         mandatory true;
         description "An opaque value of arbitrary length generated by the relay
            agent to identify one of the relay agent’s interfaces.";
       }
     }

     container reconfigure-message-option {
       if-feature "server";
       description "OPTION_RECONF_MSG (19) Reconfigure Message Option.";
       reference "RFC8415: Dynamic Host Configuration Protocol for IPv6
          (DHCPv6)";
       leaf msg-type {
         type uint8;
         description "5 for Renew message, 6 for Rebind message, 11 for
            Information-request message.";
       }
     }

     container reconfigure-accept-option {
       if-feature "server or client";
       //presence "Enable sending of this option";
       description "OPTION_RECONF_ACCEPT (20)  Rapid Commit Option. A client uses
          the Reconfigure Accept option to announce to the server whether the
          client is willing to accept Reconfigure messages, and a server uses this
          option to tell the client whether or not to accept Reconfigure messages.
          In the absence of this option, the default behavior is that the client
          is unwilling to accept Reconfigure messages.
          The presence node is used to enable the option.";
       reference "RFC8415: Dynamic Host Configuration Protocol for IPv6
          (DHCPv6)";
     }

     container info-refresh-time-option {
       if-feature "server";
       description "OPTION_INFORMATION_REFRESH_TIME (32) Information Refresh
          Time option.";
       reference "RFC8415: Dynamic Host Configuration Protocol for
          IPv6 (DHCPv6)";
       leaf info-refresh-time {
         type dhcpv6-types:timer-value-seconds32;
         mandatory true;
         description "Time duration relative to the current time, expressed in
            units of seconds.";
       }
     }

     container sol-max-rt-option {
       if-feature "server";
       description "OPTION_SOL_MAX_RT (82) sol max rt option";
       reference "RFC8415: Dynamic Host Configuration Protocol for
          IPv6 (DHCPv6)";
       leaf sol-max-rt-value {
         type dhcpv6-types:timer-value-seconds32;
         mandatory true;
         description "sol max rt value";
       }
     }

     container inf-max-rt-option {
       if-feature "server";
       description "OPTION_INF_MAX_RT (83) inf max rt option";
       reference "RFC8415: Dynamic Host Configuration Protocol for
          IPv6 (DHCPv6)";
       leaf inf-max-rt-value {
         type dhcpv6-types:timer-value-seconds32;
         mandatory true;
         description "inf max rt value";
       }
     }
  }
}
