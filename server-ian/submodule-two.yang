submodule submodule-two {
  belongs-to top {
    prefix "t";
  }

  import ietf-yang-types {
    prefix "yang";
  }

  grouping two {
    container something-else {
      leaf a-string {
        type string;
      }
      leaf a-mac-address {
        type yang:mac-address;
      }
    }
  }
}
