module example-dhcpv6-options-rfc3319 {
  yang-version 1.1;
  namespace "urn:ietf:params:xml:ns:yang:example-dhcpv6-options-rfc3319";
  prefix "rfc3319";

  import ietf-inet-types {
    prefix inet;
  }

  import ietf-dhcpv6-server {
    prefix dhcpv6-server;
  }

  organization "DHC WG";
  contact
    "ian.farrer@telekom.de
    godfryd@isc.org";

  description "This YANG module contains DHCPv6 options defined
    in RFC3319 that can be used by DHCPv6 servers.";

  revision 2020-05-26 {
    description "Version update for draft -11 publication and
      to align revisions across the different modules.";
    reference "I-D: draft-ietf-dhc-dhcpv6-yang-11";
  }

  revision 2019-10-18 {
    description "Initial version.";
    reference "I-D: draft-ietf-dhc-dhcpv6-yang";
  }

  /*
   * Groupings
   */

  grouping sip-server-domain-name-list-option-group {
    container sip-server-domain-name-list-option {
      description "OPTION_SIP_SERVER_D (21) SIP Servers Domain Name
        List";
      reference "RFC3319: Dynamic Host Configuration Protocol
        (DHCPv6) Options for Session Initiation Protocol (SIP)
        Servers";
      leaf sip-serv-domain-name {
        type inet:domain-name;
        description "sip server domain name";
      }
    }
  }

  grouping sip-server-address-list-option-group {
    container sip-server-address-list-option {
      description "OPTION_SIP_SERVER_A (22) SIP Servers IPv6 Address
        List";
      reference "RFC3319: Dynamic Host Configuration Protocol
        (DHCPv6) Options for Session Initiation Protocol (SIP)
        Servers";
      list sip-server {
        key sip-serv-id;
        description "sip server info";
        leaf sip-serv-id {
          type uint8;
          description "sip server id";
        }
        leaf sip-serv-addr {
          type inet:ipv6-address;
          description "sip server addr";
        }
      }
    }
  }
  
  /*
   * Augmentations
   */

  augment "/dhcpv6-server:dhcpv6-server/dhcpv6-server:option-sets/dhcpv6-server:option-set" {
    when "../../../dhcpv6-server:dhcpv6-node-type='dhcpv6-server:server'";
    uses sip-server-domain-name-list-option-group;
    uses sip-server-address-list-option-group;
  }
}
