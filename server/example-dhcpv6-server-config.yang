module example-dhcpv6-server-config {
  yang-version 1.1;
  namespace "urn:ietf:params:xml:ns:yang:example-dhcpv6-server-config";
  prefix "dhcpv6-server-config";

  import ietf-inet-types {
    prefix inet;
  }
  import ietf-yang-types {
    prefix yang;
  }
  import ietf-interfaces {
    prefix if;
  }
  import ietf-dhcpv6-common {
    prefix dhcpv6-common;
  }
  import ietf-dhcpv6-server {
    prefix dhcpv6-server;
  }

  organization "DHC WG";
  contact
    "cuiyong@tsinghua.edu.cn
    lh.sunlinh@gmail.com
    ian.farrer@telekom.de
    sladjana.zechlin@telekom.de
    hezihao9512@gmail.com";

  description "This model defines a YANG data model that can be
    used to configure and manage a DHCPv6 server.";

  revision 2019-06-04 {
    description "";
    reference "I-D: draft-ietf-dhc-dhcpv6-yang";
  }

  /*
   * Typedef
   */

  /*
   * Data Nodes
   */
  /*
   * Configuration data
   */
  grouping config {
    description "Parameters necessary for the configuration of a DHCPv6
      server";
    container serv-attributes {
      description
        "This container contains basic attributes of a DHCPv6 server
        such as IPv6 address, server name  and so on. Some optional
        functions that can be provided  by the server is also included.";
      container duid {
        description "Sets the DUID of server";
        uses dhcpv6-common:duid;
      }
      leaf name {
        type string;
        description "Name of the DHCpv6 server";
      }
      leaf description {
        type string;
        description "Description of the DHCPv6 server";
      }
      leaf-list ipv6-address {
        type inet:ipv6-address;
        description "List of IPv6 address(es) the server will ";
      }
      leaf-list interfaces-config {
        // Note - this should probably be references to
        // entries in the ietf-interfaces model
        type if:interface-ref;
        description "A leaf list to denote which one or more interfaces
          the server should listen on. The default value is to listen
          on all the interfaces. This node is also used to set a unicast
          address for the server to listen with a specific interface.
          For example, if people want the server to listen on a unicast
          address with a specific interface, he can use the format like
          'eth1/2001:db8::1'.";
      }
      container lease-storage {
        description "Indicates how the server stores the lease";
        choice storage-type {
          description "the type of lease storage";
          // leaf persist {
          // 		type boolean;
          // 		mandatory true;
          // 		description "controls whether the new leases and updates to existing leases are
          // 		written to the file";
          // }
          case memfile {
            description "the server stores lease information in a CSV file";

            leaf memfile-name {
              type string;
              description "specifies an absolute location of the lease file in which new leases
                and lease updates will be recorded";
            }

            leaf memfile-lfc-interval {
              type uint64;
              description "specifies the interval in seconds, at which the server will perform a
                lease file cleanup (LFC)";
            }
          }
          case mysql {
            leaf mysql-name {
              type string;
              description "type of the database";
            }
            leaf mysql-host {
              type string;
              description "If the database is located
                on a different system to the DHCPv6 server, the database host name must also be specified.";
            }
            leaf mysql-password {
              type string;
              description "the credentials of the account under which the server will access the database";
            }
            leaf mysql-port {
              type uint8;
              description "If the database is located on a different system, the port number may be specified";
            }
            leaf mysql-lfc-interval {
              type uint64;
              description "specifies the interval in seconds, at which the server will perform a
                lease file cleanup (LFC)";
            }
            leaf mysql-connect-timeout {
              type uint64;
              description "If the database is located on a different system, a longer interval needs to be specified";
            }
          }
          case postgresql {
            leaf postgresql-name {
              type string;
              description "type of the database";
            }
            leaf postgresql-host {
              type string;
              description "If the database is located
                on a different system to the DHCPv6 server, the database host name must also be specified.";
            }
            leaf postgresql-password {
              type string;
              description "the credentials of the account under which the server will access the database";
            }
            leaf postgresql-port {
              type uint8;
              description "If the database is located on a different system, the port number may be specified";
            }
            leaf postgresql-lfc-interval {
              type uint64;
              description "specifies the interval in seconds, at which the server will perform a
                lease file cleanup (LFC)";
            }
            leaf postgresql-connect-timeout {
              type uint64;
              description "If the database is located on a different system, a longer interval needs to be specified";
            }
          }
          case cassandra {
            leaf cassandra-name {
              type string;
              description "type of the database";
            }
            leaf cassandra-contact-points {
              type string;
              description "Cassandra takes a list of comma separated IP addresses to contact the cluster";
            }
            leaf cassandra-password {
              type string;
              description "the credentials of the account under which the server will access the database";
            }
            leaf cassandra-lfc-interval {
              type uint64;
              description "specifies the interval in seconds, at which the server will perform a
                lease file cleanup (LFC)";
            }
            leaf cassandra-connect-timeout {
              type uint64;
              description "If the database is located on a different system, a longer interval needs to be specified";
            }
          }
        }
      }
      uses dhcpv6-common:vendor-infor;
    }

    /*
     * Notifications
     */

  }

  augment "/dhcpv6-server:config/dhcpv6-server:vendor-config" {
    uses dhcpv6-server-config:config;
  }
}
