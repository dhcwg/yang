module ietf-dhcpv6-client {
  yang-version 1.1;
  namespace "urn:ietf:params:xml:ns:yang:ietf-dhcpv6-client";
  prefix "dhcpv6-client";

  import ietf-dhcpv6-common {
    prefix dhcpv6-common;
  }

  import ietf-interfaces {
    prefix if;
  }

  organization "DHC WG";
  contact
    "cuiyong@tsinghua.edu.cn
    wangh13@mails.tsinghua.edu.cn
    lh.sunlinh@gmail.com
    ian.farrer@telekom.de
    sladjana.zechlin@telekom.de
    hezihao9512@gmail.com";

  description "This is a YANG data module for the configuration and management
    of DHCPv6 clients.

    Copyright (c) 2018 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC 8513; see
    the RFC itself for full legal notices.";

  revision 2018-09-04 {
    description "";
    reference "I-D: draft-ietf-dhc-dhcpv6-yang";
  }

  revision 2018-03-04 {
    description "Resolved most issues on the DHC official
      github";
    reference "I-D: draft-ietf-dhc-dhcpv6-yang";
  }

  revision 2017-12-22 {
    description "Resolve most issues on Ian's github.";
    reference "I-D: draft-ietf-dhc-dhcpv6-yang";
  }

  revision 2017-11-24 {
    description "First version of the separated client specific
      YANG model.";
    reference "I-D: draft-ietf-dhc-dhcpv6-yang";
  }

  identity client {
    base "dhcpv6-common:dhcpv6-node";
    description "DHCPv6 client.";
  }

  leaf dhcpv6-node-type {
    description "Type for a DHCPv6 client";
    type identityref {
      base "dhcpv6-client:client";
    }
  }

  /*
   * Data Nodes
   */

  container config {
    description "Configuration tree of client";
    container duid {
      description "Sets the DUID";
      uses dhcpv6-common:duid;
    }
    list client-if {
      key if-name;
      description "A client may have several interfaces, it is more reasonable to
        configure and manage parameters on the interface-level. The list defines
        specific client interfaces and their data. Different interfaces are
        distinguished by the key which is a configurable string value.";
      leaf if-name {
        type if:interface-ref;
        mandatory true;
        description "Interface name";
      }
      leaf client-id {
        type uint32;
        mandatory true;
        description "Client ID";
      }
      leaf pd-function {
        type boolean;
        mandatory true;
        description "Whether the client can act as a requesting router
          to request prefixes using prefix delegation ([RFC3633]).";
      }
      leaf rapid-commit {
        type boolean;
        mandatory true;
        description "'1' indicates a client can initiate a Solicit-Reply message
          exchange by adding a Rapid Commit option in Solicit message. '0' means
          the client is not allowed to add a Rapid Commit option to request
          addresses in a two-message exchange pattern.";
      }

      /*
         container mo-tab {
         description "The management tab label indicates the operation mode of the
         DHCPv6 client.
         'm'=1 and 'o'=1 indicate the client will use DHCPv6 to  obtain all the configuration
         data.
         'm'=1 and 'o'=0 are a meaningless combination.
         'm'=0 and 'o'=1 indicate the client will use stateless DHCPv6 to obtain configuration
         data apart from addresses/prefixes data.
         'm'=0 and 'o'=0 represent the client will not use DHCPv6 but use SLAAC to
         achieve configuration.";

      // if - not sure about the intended use here as it seems
      // to be redfining what will be received in the PIO. Is
      // the intention to be whether they PIO options will be
      // obeyed as received or overridden?
      leaf m-tab {
      type boolean;
      mandatory true;
      description "m tab";
      }
      leaf o-tab {
      type boolean;
      mandatory true;
      description "o tab";
      }
      }
       */

      container client-configured-options {
        description "Definitions for client DHCPv6 options are augmented
          from other modules at this location.";
      }
    }
  }

  container client-state {
    config "false";
    description "state tree of client";
    container if-other-parameters {
      description "A client can obtain extra configuration
        data other than address and prefix information through
        DHCPv6. This container describes such data the client
        was configured. The potential configuration data may
        include DNS server addresses, SIP server domain names, etc.";
      //uses dhcpv6-options:server-option-definitions;
    }
    container packet-statistics {
      config "false";
      description "A container records
        all the packet status information
        of a specific interface.";
      leaf solicit-count {
        type uint32;
        mandatory true;
        description "Solicit packets count";
      }
      leaf request-count {
        type uint32;
        mandatory true;
        description "Request packets count";
      }
      leaf renew-count {
        type uint32;
        mandatory true;
        description "Renew packets count";
      }
      leaf rebind-count {
        type uint32;
        mandatory true;
        description "Rebind packets count";
      }
      leaf decline-count {
        type uint32;
        mandatory true;
        description "Decline packets count";
      }
      leaf release-count {
        type uint32;
        mandatory true;
        description "Release packets count";
      }
      leaf info-request-count {
        type uint32;
        mandatory true;
        description "Information request packets count";
      }
      leaf advertise-count {
        type uint32;
        mandatory true;
        description "Advertise packets count";
      }
      leaf confirm-count {
        type uint32;
        mandatory true;
        description "Confirm packets count";
      }
      leaf reply-count {
        type uint32;
        mandatory true;
        description "Reply packets count";
      }
      leaf reconfigure-count {
        type uint32;
        mandatory true;
        description "Recofigure packets count";
      }
    }
  }

  /*
   * Notifications
   */

  notification ia-lease-event {
    description "Notification sent when the client was allocated
          a new IA from the server or it renew/rebind/release
          its current IA";
    leaf event-type {
      type enumeration {
        enum "allocation" {
          description "allocate";
        }
        enum "rebind" {
          description "rebind";
        }
        enum "renew" {
          description "renew";
        }
        enum "release" {
          description "release";
        }
      }
      mandatory true;
      description "event type";
    }
    leaf iaid {
      type uint32;
      mandatory true;
      description "IAID";
    }
    container duid {
      description "Server's DUID";
      uses dhcpv6-common:duid;
    }
  }

  notification invalid-ia-detected {
    description "Notification sent when the identity association of the
          client can be proved to be invalid.  Possible condition
          includes duplicated address, illegal address, etc.";
    leaf iaid {
      type uint32;
      mandatory true;
      description "IAID";
    }
    leaf description {
      type string;
      description "Description of the event";
    }
  }

  notification retransmission-failed {
    description "Notification sent when the retransmission mechanism defined
          in [RFC3315] is failed.";
    leaf description {
      type enumeration {
        enum "MRC failed" {
          description "MRC failed";
        }
        enum "MRD failed" {
          description "MRD failed";
        }
      }
      mandatory true;
      description "Description of failure";
    }
  }

  notification failed-status-turn-up {
    description "Notification sent when the client receives a message includes
          an unsuccessful Status Code option.";
    leaf status-code {
      type uint16;
      mandatory true;
      description "Status code recevied by a client";
    }
    container duid {
      description "Server's DUID";
      uses dhcpv6-common:duid;
    }
  }
}
