module ietf-dhcpv6-classifying {
  yang-version 1.1;
  namespace "urn:ietf:params:xml:ns:yang:ietf-dhcpv6-classifying";
  prefix "dhcpv6-classifying";

  import ietf-inet-types {
    prefix inet;
  }
  import ietf-interfaces {
    prefix if;
  }
  import ietf-dhcpv6-types {
    prefix dhcpv6-types;
  }

  import ietf-dhcpv6-server {
    prefix dhcpv6-server;
  }

  organization "DHC WG";
  contact
    "yong@csnet1.cs.tsinghua.edu.cn
    lh.sunlinh@gmail.com
    ian.farrer@telekom.de
    sladjana.zechlin@telekom.de
    hezihao9512@gmail.com";

  description "This model defines a YANG data model that can be
    used to define client classifying.";

  revision 2019-06-13 {
    description "";
    reference "I-D: draft-ietf-dhc-dhcpv6-yang";
  }


  grouping client-class-id {
    description "Defintions for client classification for authorization and assignment
      purposes.";

    // selection based on:
    // - text-literal - TODO: how does it work?
    // - received-interface - e.g. eth0
    // - packet-source-address
    // - packet-dst-address
    // - relay-link-address (TODO: but is ipv6-prefix)
    // - relay-peer-address (TODO: but is ipv6-prefix)
    // - vendor-class-present option-16
    // - vendor-class-option-ent-num-id option-16
    // - ent-num/vendor-class-data option-16
    // - client-duid-id
    // NEW:
    // - user-class option-15
    // - interface-id option-18
    // - remote-id option-37 (ent-num/remote-id)

    leaf client-class-name {
      type string;
      description "Unique Identifier for client class
                    identification list entries.";
    }

    choice id-type {
      description "Definitions for different client identifier types.";
      mandatory true; // TODO: is it needed
      case text-literal-id { // TODO: how does it work?
        description "Client class selection based on a string literal client
          identifier.";
        leaf text-literal {
          description "String literal client identifier.";
          mandatory true; // TODO: is it needed
          type string;
        }
      }
      case received-interface-id {
        description "Client class selection based on the incoming interface of
          the DHCPv6 message.";
        leaf received-interface {
          description "Reference to the interface entry for the incoming
            DHCPv6 message.";
          type if:interface-ref;
        }
      }
      case packet-source-address-id {
        description "Client class selection based on the source address of
          the DHCPv6 message.";
        leaf  packet-source-address {
          description "Source address of the DHCPv6 message.";
          mandatory true;
          type inet:ipv6-address;
        }
      }
      case packet-dst-address-id {
        description "Client class selection based on the destination address of
          the DHCPv6 message.";
        leaf  packet-dst-address {
          description "Destination address of the DHCPv6 message.";
          mandatory true;
          type inet:ipv6-address;
        }
      }
      case relay-link-address-id {
        description "Client class selection based on the prefix of the
          link-address field in the relay agent message header.";
        leaf relay-link-address {
          description "Prefix of the link-address field in the relay agent
            message header.";
          mandatory true;
          type inet:ipv6-prefix;
        }
      }
      case relay-peer-address-id {
        description "Client class selection based on the value of the
          peer-address field in the relay agent message header.";
        leaf relay-peer-address {
          description "Prefix of the peer-address field in the relay agent
            message header.";
          mandatory true;
          type inet:ipv6-prefix;
        }
      }
      case relay-interface-id { // NEW
        description "Client class selection based on the incoming interface-id option.";
        leaf relay-interface-id {
          description "Reference to the interface entry for the incoming
            DHCPv6 message.";
          type string;
        }
      }
      case user-class-option-id { // NEW
        description "Client class selection based on the value of the
          OPTION_USER_CLASS(15) and its user-class-data field.";
        leaf user-class-data {
          description "Value of the enterprise-number field.";
          mandatory true;
          type string;
        }
      }
      case vendor-class-present-id {
        description "Client class selection based on the presence of
          OPTION_VENDOR_CLASS(16) in the received message.";
        leaf vendor-class-present {
          description "Presence of OPTION_VENDOR_CLASS(16) in the received
            message.";
          mandatory true;
          type boolean;
        }
      }
      case vendor-class-option-ent-num-id {
        description "Client class selection based on the value of the
          enterprise-number field in OPTION_VENDOR_CLASS(16).";
        leaf ent-num { // TODO: name should be more descriptive e.g. vendor-class-option-ent-num
          description "Value of the enterprise-number field.";
          mandatory true;
          type uint32;
        }
      }
      case vendor-class-option-data-id {
        description "Client class selection based on the value of a data field
          within a vendor-class-data entry for a matching enterprise-number
          field in OPTION_VENDOR_CLASS(16).";
        container vendor-class-option-data {
          leaf ent-num {
            description "Value of the enterprise-number field for matching the
              data contents.";
            mandatory true;
            type uint32;
          }
          leaf vendor-class-data {
            description "Vendor class data to match.";
            mandatory true;
            type string;
          }
        }
      }
      case remote-id { // NEW
        description "Client class selection based on the value TODO .";
        container remote-id {
          leaf ent-num {
            description "Value of the enterprise-number field for matching the
              data contents.";
            mandatory true;
            type uint32;
          }
          leaf remote-id {
            description "Remote-ID data to match.";
            mandatory true;
            type string;
          }
        }
      }
      case client-duid-id {
        description "Client class selection based on the value of the received
          client DUID.";
        uses dhcpv6-types:duid;
      }
    }
  }
}
