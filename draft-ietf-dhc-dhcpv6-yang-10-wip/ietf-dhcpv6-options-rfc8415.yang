module ietf-dhcpv6-options-rfc8415 {
  yang-version 1.1;
  namespace "urn:ietf:params:xml:ns:yang:ietf-dhcpv6-options-8415";
  prefix "rfc8415";

  import ietf-inet-types {
    prefix inet;
  }

  import ietf-dhcpv6-common {
    prefix dhcpv6-common;
  }

  import ietf-dhcpv6-server {
    prefix dhcpv6-server;
  }

  import ietf-dhcpv6-relay {
    prefix dhcpv6-relay;
  }

  import ietf-dhcpv6-client {
    prefix dhcpv6-client;
  }

  organization "DHC WG";
  contact
    "cuiyong@tsinghua.edu.cn
    wangh13@mails.tsinghua.edu.cn
    lh.sunlinh@gmail.com
    ian.farrer@telekom.de
    sladjana.zechlin@telekom.de
    hezihao9512@gmail.com";

  description "This YANG module contains DHCPv6 options defined
    in RFC8415 that can be used by DHCPv6 clients, relays
    and servers.";

  revision 2019-06-07 {
    description "Major reworking to only contain RFC8415 options.
      if-feature for each option removed. Removed groupings
      of features by device or combination of devices. Added ";
    reference "I-D: draft-ietf-dhc-dhcpv6-yang";
  }

  revision 2018-09-04 {
    description "";
    reference "I-D: draft-ietf-dhc-dhcpv6-yang";
  }

  revision 2018-03-04 {
    description "Resolved most issues on the DHC official
      github";
    reference "I-D: draft-ietf-dhc-dhcpv6-yang";
  }

  revision 2017-12-22 {
    description "Resolve most issues on Ian's github.";
    reference "I-D: draft-ietf-dhc-dhcpv6-yang";
  }

  revision 2017-11-24 {
    description "First version of the separated DHCPv6 options
      YANG model.";
    reference "I-D:draft-ietf-dhc-dhcpv6-yang";
  }

  /*
   * Features

  /*
   * Groupings
   */
  grouping option-iaaddr-option {
    description "OPTION_IAADDR (5) IA Address Option.";
    reference "RFC8415: Dynamic Host Configuration Protocol for IPv6
      (DHCPv6)";
    leaf IPv6-address {
      type inet:ipv6-address;
      description "An IPv6 address.  A client MUST NOT form
        an iplicit prefix with a length other than 128
        for this address.";
    }
    leaf preferred-lifetime {
      type uint32;
      description "The preferred lifetime for the address
        in the option, expressed in units of seconds.";
    }
    leaf valid-lifetime {
      type uint32;
      description "The preferred lifetime for the address
        in the option, expressed in units of seconds.";
    }
    container iaaddr-options {
      description "Definitions for DHCPv6 options that can be be sent
        by the client are augmented to this location from other YANG
        modules as required.";
    }
  }

  grouping option-request-option-group {
    container option-request-option {
      description "OPTION_ORO (6) Option Request Option. A client
        MUST include an Option Request option in a Solicit, Request,
        Renew, Rebind, or Information-request message to inform
        the server about options the client wants the server to send
        to the client.";
      reference "RFC8415: Dynamic Host Configuration Protocol for
        IPv6 (DHCPv6)";
      leaf-list oro-option {
        description "List of options that the client is requesting,
          identified by option code";
        type uint16 {
          range "17 | 21..24 | 27..36 | 39..42 | 49..52 | 54..60 |
            62..65 | 69..78";
        }
      }
    }
  }

  grouping preference-option-group {
    container preference-option {
      description "OPTION_PREFERENCE (7) Preference Option";
      reference "RFC8415: Dynamic Host Configuration Protocol for
        IPv6 (DHCPv6)";
      leaf pref-value {
        type uint8;
        description "The preference value for the server
          in this message. A 1-octet unsigned integer.";
      }
    }
  }

  grouping auth-option-group {
    container auth-option {
      description "OPTION_AUTH (11) Authentication Option";
      reference "RFC8415: Dynamic Host Configuration Protocol
        for IPv6 (DHCPv6)";
      leaf protocol {
        type uint8;
        description "The authentication protocol used
          in this Authentication option.";
      }
      leaf algorithm {
        type uint8;
        description "The algorithm used in the authentication
          protocol.";
      }
      leaf rdm {
        type uint8;
        description "The replay detection method used
          in this Authentication option.";
      }
      leaf replay-detection {
        type uint64;
        description "The replay detection information for the RDM.";
      }
      leaf auth-information {
        type string;
        description "The authentication information, as specified
          by the protocol and algorithm used in this Authentication
          option.";
      }
    }
  }

  grouping server-unicast-option-group {
    container server-unicast-option {
      description "OPTION_UNICAST (12) Server Unicast Option";
      reference "RFC8415: Dynamic Host Configuration Protocol for
        IPv6 (DHCPv6)";
      leaf server-address {
        type inet:ipv6-address;
        description "The 128-bit address to which the client
          should send messages delivered using unicast.";
      }
    }
  }

  grouping status-code-option-group {
    container status-code-option {
      description "OPTION_STATUS_CODE (13) Status Code Option.";
      reference "RFC8415: Dynamic Host Configuration Protocol
        for IPv6 (DHCPv6)";
      leaf status-code {
        type uint16;
        description "The numeric code for the status encoded
          in this option. See the Status Codes registry at
          <https://www.iana.org/assignments/dhcpv6-parameters>
          for the current list of status codes.";
      }
      leaf status-message {
        type string;
        description "A UTF-8 encoded text string suitable
          for display to an end user. MUST NOT be null-terminated.";
      }
    }
  }

  grouping rapid-commit-option-group {
    container rapid-commit-option {
      presence "Enable sending of this option";
      description "OPTION_RAPID_COMMIT (14) Rapid Commit Option.
        The presence node is used to enable the option.";
      reference "RFC8415: Dynamic Host Configuration Protocol for
        IPv6 (DHCPv6)";
    }
  }

  grouping user-class-option-group {
    container user-class-option {
      description "OPTION_USER_CLASS (15) User Class Option";
      reference "RFC8415: Dynamic Host Configuration Protocol
        for IPv6 (DHCPv6)";
      list user-class-data {
        key user-class-datum-id;
        min-elements 1;
        description "The user classes of which the client
          is a member.";
        leaf user-class-datum-id {
          type uint8;
          description "User class datum ID";
        }
        leaf user-class-datum {
          type string;
          description "Opaque field representing a User Class
            of which the client is a member.";
        }
      }
    }
  }

  grouping vendor-class-option-group {
    container vendor-class-option {
      description "OPTION_VENDOR_CLASS (16) Vendor Class Option";
      reference "RFC8415: Dynamic Host Configuration Protocol
        for IPv6 (DHCPv6)";
      list vendor-class-option-instances {
        key enterprise-number;
        description "The vendor class option allows for multiple
          instances in a single message. Each list entry defines
          the contents of an instance of the option.";
        leaf enterprise-number {
          type uint32;
          description "The vendor's registered Enterprise Number
            as maintained by IANA.";
        }
        list vendor-class {
          key vendor-class-datum-id;
          description "The vendor classes of which the client
            is a member.";
          leaf vendor-class-datum-id {
            type uint8;
            description "Vendor class datum ID";
          }
          leaf vendor-class-datum {
            type string;
            description "Opaque field representing a vendor class
              of which the client is a member.";
          }
        }
      }
    }
  }

  grouping vendor-specific-information-option-group {
    container vendor-specific-information-option {
      description "OPTION_VENDOR_OPTS (17) Vendor-specific
        Information Option";
      reference "RFC8415: Dynamic Host Configuration Protocol
        for IPv6 (DHCPv6)";
      list vendor-specific-information-option-instances {
        key enterprise-number;
        description "The vendor specific information option allows
          for multiple instances in a single message. Each list entry
          defines the contents of an instance of the option.";
        leaf enterprise-number {
          type uint32;
          description "The vendor's registered Enterprise Number,
            as maintained by IANA.";
        }
        list vendor-option-data {
          key sub-option-code;
          description "Vendor options, interpreted by vendor-specific
            client/server functions.";
          leaf sub-option-code {
            type uint16;
            description "The code for the sub-option.";
          }
          leaf sub-option-data {
            type string;
            description "The data area for the sub-option.";
          }
        }
      }
    }
  }

  grouping interface-id-option-group {
    container interface-id-option {
      description "OPTION_INTERFACE_ID (18) Interface-Id Option";
      reference "RFC8415: Dynamic Host Configuration Protocol for
        IPv6 (DHCPv6)";
      leaf interface-id {
        type string;
        description "An opaque value of arbitrary length generated
          by the relay agent to identify one of the relay agent's
          interfaces.";
      }
    }
  }

  grouping reconfigure-message-option-group {
    container reconfigure-message-option {
      description "OPTION_RECONF_MSG (19) Reconfigure Message
        Option.";
      reference "RFC8415: Dynamic Host Configuration Protocol
        for IPv6 (DHCPv6)";
      leaf msg-type {
        type uint8;
        description "5 for Renew message, 6 for Rebind message,
          11 for Information-request message.";
      }
    }
  }

  grouping reconfigure-accept-option-group {
    container reconfigure-accept-option {
      presence "Enable sending of this option";
      description "OPTION_RECONF_ACCEPT (20)  Rapid Commit Option.
        A client uses the Reconfigure Accept option to announce
        to the server whether the client is willing to accept
        Reconfigure messages, and a server uses this option to tell
        the client whether or not to accept Reconfigure messages.
        In the absence of this option, the default behavior is that
        the client is unwilling to accept Reconfigure messages.
        The presence node is used to enable the option.";
      reference "RFC8415: Dynamic Host Configuration Protocol
        for IPv6 (DHCPv6)";
    }
  }

  grouping option-iaprefix-option {
    description "OPTION_IAPREFIX (26) IA Address Option.";
    reference "RFC8415: Dynamic Host Configuration Protocol for IPv6
      (DHCPv6)";
    leaf preferred-lifetime {
      type uint32;
      description "The preferred lifetime for the prefix
        in the option, expressed in units of seconds.";
    }
    leaf valid-lifetime {
      type uint32;
      description "The preferred lifetime for the prefix
        in the option, expressed in units of seconds.";
    }
    leaf IPv6-prefix {
      type inet:ipv6-prefix;
      description "The IPv6 prefix delegated to the client.";
    }
    container iaprefix-options {
      description "Definitions for DHCPv6 options that can be
        sent by the client are augmented to this location from other
        YANG modules as required.";
    }
  }

  grouping info-refresh-time-option-group {
    container info-refresh-time-option {
      description "OPTION_INFORMATION_REFRESH_TIME (32)
        Information Refresh Time option.";
      reference "RFC8415: Dynamic Host Configuration Protocol for
        IPv6 (DHCPv6)";
      leaf info-refresh-time {
        type dhcpv6-common:timer-value-seconds32;
        description "Time duration relative to the current time,
          expressed in units of seconds.";
      }
    }
  }

  grouping sol-max-rt-option-group {
    container sol-max-rt-option {
      description "OPTION_SOL_MAX_RT (82) sol max rt option";
      reference "RFC8415: Dynamic Host Configuration Protocol for
        IPv6 (DHCPv6)";
      leaf sol-max-rt-value {
        type dhcpv6-common:timer-value-seconds32;
        description "sol max rt value";
      }
    }
  }

  grouping inf-max-rt-option-group {
    container inf-max-rt-option {
      description "OPTION_INF_MAX_RT (83) inf max rt option";
      reference "RFC8415: Dynamic Host Configuration Protocol for
        IPv6 (DHCPv6)";
      leaf inf-max-rt-value {
        type dhcpv6-common:timer-value-seconds32;
        description "inf max rt value";
      }
    }
  }

  augment "/dhcpv6-server:dhcpv6-server/dhcpv6-server:option-sets/dhcpv6-server:option-set" {
    when "../../../dhcpv6-server:dhcpv6-node-type='dhcpv6-server:server'";
    uses preference-option-group;
    uses auth-option-group;
    uses server-unicast-option-group;
    uses status-code-option-group;
    uses rapid-commit-option-group;
    uses vendor-specific-information-option-group;
    uses reconfigure-message-option-group;
    uses reconfigure-accept-option-group;
    uses info-refresh-time-option-group;
    uses sol-max-rt-option-group;
    uses inf-max-rt-option-group;
  }
  augment "/dhcpv6-relay:dhcpv6-relay/dhcpv6-relay:relay-if/dhcpv6-relay:relay-options" {
    when "../../../dhcpv6-relay:dhcpv6-node-type='dhcpv6-relay:relay'";
    uses auth-option-group;
    uses status-code-option-group;
    uses interface-id-option-group;
  }
  augment "/dhcpv6-client:dhcpv6-client/dhcpv6-client:client-if/dhcpv6-client:client-configured-options" {
    when "../../../dhcpv6-client:dhcpv6-node-type='dhcpv6-client:client'";
    uses option-request-option-group;
    uses status-code-option-group;
    uses rapid-commit-option-group;
    uses user-class-option-group;
    uses vendor-class-option-group;
    uses vendor-specific-information-option-group;
    uses reconfigure-accept-option-group;
  }
}
