module ietf-dhcpv6-server {
  yang-version 1.1;
  namespace "urn:ietf:params:xml:ns:yang:ietf-dhcpv6-server";
  prefix "dhcpv6-server";

  import ietf-inet-types {
    prefix inet;
  }
  import ietf-yang-types {
    prefix yang;
  }
  import ietf-dhcpv6-common {
    prefix dhcpv6-common;
  }

  organization "DHC WG";
  contact
    "cuiyong@tsinghua.edu.cn
    lh.sunlinh@gmail.com
    ian.farrer@telekom.de
    sladjana.zechlin@telekom.de
    hezihao9512@gmail.com
    godfryd@isc.org";

  description "This is a YANG data module for the configuration
    and management of DHCPv6 servers.

    Copyright (c) 2018 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC 8513; see
    the RFC itself for full legal notices.";

  revision 2018-09-04 {
    description "";
    reference "I-D: draft-ietf-dhc-dhcpv6-yang";
  }

  revision 2018-03-04 {
    description "Resolved most issues on the DHC official
      github";
    reference "I-D: draft-ietf-dhc-dhcpv6-yang";
  }

  revision 2017-12-22 {
    description "Resolve most issues on Ian's github.";
    reference "I-D: draft-ietf-dhc-dhcpv6-yang";
  }

  revision 2017-11-24 {
    description "First version of the separated server specific
      YANG model.";
    reference "I-D: draft-ietf-dhc-dhcpv6-yang";
  }

  /*
   * Typedef
   */

  identity server {
    base "dhcpv6-common:dhcpv6-node";
    description "DHCPv6 server.";
  }

  leaf dhcpv6-node-type {
    description "Type for a DHCPv6 server";
    type identityref {
      base "dhcpv6-server:server";
    }
  }

  feature prefix-delegation {
    description "Enable if the server implements prefix delegation.";
  }

  grouping resource-config {
    description "Nodes that are reused by multiple levels
      in the DHCPv6 server's addressing hierarchy.";
    leaf-list option-set-id {
      type leafref {
        path "/dhcpv6-server/option-sets/option-set/option-set-id";
      }
      description "The ID field of relevant option-set
        to be provisioned to clients of this network-range.";
    }
    leaf valid-lifetime {
      type dhcpv6-common:timer-value-seconds32;
      mandatory true;
      description "Valid lifetime for the IA.";
    }
    leaf renew-time {
      type dhcpv6-common:timer-value-seconds32;
      mandatory true;
      description "Renew (T1) time.";
    }
    leaf rebind-time {
      type dhcpv6-common:timer-value-seconds32;
      mandatory true;
      description "Rebind (T2) time.";
    }
    leaf preferred-lifetime {
      type dhcpv6-common:timer-value-seconds32;
      mandatory true;
      description "Preferred lifetime for the IA";
    }
    leaf rapid-commit {
      type boolean;
      mandatory true;
      description "A value of 1 specifies that the pool supports
        client-server exchanges involving two messages.";
    }
  }

  grouping lease-information {
    leaf total-address-count {
      type uint64;
      mandatory true;
      description "Count of total addresses in the pool";
    }
    leaf allocated-address-count {
      type uint64;
      mandatory true;
      description "Count of allocated addresses in the pool";
    }
    list binding-info {
      key client-duid;
      description "Records binding information for each client that
        has previously been allocated IPv6 addresses.";
      leaf client-duid {
        description "Client DUID.";
        type binary;
      }
      list iaid {
        key iaid;
        description "Clients IAID.";
        leaf iaid {
          type uint32;
          mandatory true;
          description "IAID";
        }
        leaf allocation-time {
          description "Time and date that the lease was made.";
          type yang:date-and-time;
        }
        leaf last-renew-rebind {
          description "Time of the last successful renew or rebind.";
          type yang:date-and-time;
        }
        leaf preferred-lifetime {
          description "The preferred lifetime expressed in units
            of seconds.";
          type dhcpv6-common:timer-value-seconds32;
        }
        leaf valid-lifetime {
          description "The valid lifetime for the leased prefix
            expressed in units of seconds.";
          type dhcpv6-common:timer-value-seconds32;
        }
        leaf lease-t1 {
          description "The time interval after which the client
            should contact the server from which the addresses
            in the IA_NA were obtained to extend the lifetimes
            of the addresses assigned to the IA_PD.";
          type dhcpv6-common:timer-value-seconds32;
        }
        leaf lease-t2 {
          description "The time interval after which the client
            should contact any available server to extend
            the lifetimes of the addresses assigned to the IA_PD.";
          type dhcpv6-common:timer-value-seconds32;
        }
      }
    }
  }

  grouping message-stats {
    description "Counters for DHCPv6 messages.";
    leaf solicit-count {
      config "false";
      type uint32;
      description "Number of Solicit (1) messages received.";
    }
    leaf advertise-count {
      config "false";
      type uint32;
      description "Number of Advertise (2) messages sent.";
    }
    leaf request-count {
      config "false";
      type uint32;
      description "Number of Request (3) messages received.";
    }
    leaf confirm-count {
      config "false";
      type uint32;
      description "Number of Confirm (4) messages received.";
    }
    leaf renew-count {
      config "false";
      type uint32;
      description "Number of Renew (5) messages received.";
    }
    leaf rebind-count {
      config "false";
      type uint32;
      description "Number of Rebind (6) messages received.";
    }
    leaf reply-count {
      config "false";
      type uint32;
      description "Number of Reply (7) messages sent.";
    }
    leaf release-count {
      type uint32;
      description "Number of Release (8) messages received.";
    }
    leaf decline-count {
      config "false";
      type uint32;
      description "Number of Decline (9) messages received.";
    }
    leaf reconfigure-count {
      config "false";
      type uint32;
      description "Number of Reconfigure (10) messages sent.";
    }
    leaf information-request-count {
      config "false";
      type uint32;
      description "Number of Information-request (11) messages
        received.";
    }
  }

  /*
   * Data Nodes
   */
  container dhcpv6-server {
    container server-duid {
      description "DUID of the server.";
      uses dhcpv6-common:duid;
    }
    container vendor-config {
      description "This container provides a location for augmenting
        vendor or implementation specific configuration nodes.";
    }
    container option-sets {
      description "A server may allow different option sets
        to be configured for clients matching specific parameters
        such as topological location or client type. The 'option-set'
        list is a set of options and their contents that
        will be returned to clients.";
      list option-set {
        key option-set-id;
        description "YANG definitions for DHCPv6 options are
          contained in separate YANG modules and augmented to this
          container as required.";
        leaf option-set-id {
          type uint32;
          description "Option set identifier.";
        }
        leaf description {
          type string;
          description "An optional field for storing additional
            information relevant to the option set.";
        }
      }
    }

    container class-selector {
      description "DHCPv6 servers use a 'class-selector' function
        in order to identify and classify incoming client messages
        so that they can be given the correct configuration.
        The mechanisms used for implementing this function vary
        greatly between different implementations such that they are
        not possible to include in this module. This container
        provides a location for server implementors to augment their
        own class-selector YANG.";
    }

    container network-ranges {
      description "This model supports a hierarchy to achieve dynamic
        configuration. That is to say we could configure the server
        at different levels through this model. The top level is
        a global level which is defined as the container
        'network-ranges'. The following levels are defined
        as sub-containers under it. The 'network-ranges' contains the
        parameters (e.g. option-sets) that would be allocated to
        all the clients served by this server.";
      uses resource-config;
      list network-range {
        key network-range-id;
        description "Under the 'network-ranges' container,
          a 'network-range' list is defined to configure the server
          at a network level which is also considered as the second
          level. Different network are identified by the key
          'network-range-id'. This is because a server may have
          different configuration parameters (e.g. option sets)
          for different networks.";
        leaf network-range-id {
          type uint32;
          mandatory true;
          description "Equivalent to subnet ID";
        }
        leaf network-description {
          type string;
          mandatory true;
          description "Description of the network range.";
        }
        leaf network-prefix {
          type inet:ipv6-prefix;
          mandatory true;
          description "Network prefix";
        }
        uses resource-config;
        container address-pools {
          description
            "A container that describes the DHCPv6 server's
            address pools.";
          list address-pool {
            key pool-id;
            description "A DHCPv6 server can be configured with
              several address pools. This list defines such address
              pools which are distinguished by the key called
              'pool-id'.";
            leaf pool-id {
              type uint32;
              mandatory true;
              description "Pool ID";
            }
            leaf pool-prefix {
              type inet:ipv6-prefix;
              mandatory true;
              description "Pool prefix";
            }
            leaf start-address {
              type inet:ipv6-address-no-zone;
              mandatory true;
              description "Start address";
            }
            leaf end-address {
              type inet:ipv6-address-no-zone;
              mandatory true;
              description "End address";
            }
            leaf max-address-count {
              type dhcpv6-common:threshold;
              mandatory true;
              description "Maximum count of addresses that can
                be allocated in this pool. This value may be
                less than count of total addresses.";
            }
            uses resource-config;
            container host-reservations {
              description "Configuration for host reservations
                in the address pool.";
              list host-reservation {
                key reserved-address;
                leaf client-duid {
                  type binary;
                  description "Client DUID.";
                }
                leaf address {
                  type inet:ipv6-address;
                  description "Reserved address";
                }
                list prefix-reservation {
                  key prefix-id;
                  description "Reserved prefix";
                  leaf prefix-id {
                    type uint32;
                    mandatory true;
                    description "Prefix id";
                  }
                  leaf prefix {
                    type inet:ipv6-prefix;
                    mandatory true;
                    description "Prefix";
                  }
                  leaf prefix-len {
                    type uint8;
                    mandatory true;
                    description "Prefix length";
                  }
                }
                uses resource-config;
              }
            }
            list active-leases {
              description "Holds state for active client leases.";
              config false;
              key leased-address;
              leaf leased-address {
                type inet:ipv6-address;
              }
              uses lease-information;
            }
          }
        }
        container prefix-pools {
          description "Defines IPv6 prefix pools to be delegated
            to clients.";
          if-feature prefix-delegation;
          list prefix-pool {
            key pool-id;
            description "A server can be configured with multiple
              prefix pools.";
            leaf pool-id {
              type uint32;
              mandatory true;
              description "Unique identfier for the pool.";
            }
            leaf prefix {
              type inet:ipv6-prefix;
              mandatory true;
              description "IPv6 prefix";
            }
            leaf prefix-length {
              type uint8;
              mandatory true;
              description "Length of prefixes that will be delegated
                to clients.";
            }
            leaf max-pd-space-utilization {
              type dhcpv6-common:threshold;
              mandatory true;
              description "Maximum utilization of PD space
                in this pool";
            }
            uses resource-config;
            container host-reservations {
              description "Configuration for host reservations
                in the prefix pool.";
              list prefix-reservation {
                description "reserved prefix reservation";
                key prefix;
                leaf client-duid {
                  type binary;
                  description "Client DUID.";
                }
                leaf prefix {
                  type inet:ipv6-prefix;
                  mandatory true;
                  description "Prefix";
                }
                leaf prefix-len {
                  type uint8;
                  mandatory true;
                  description "Prefix length";
                }
              }
              uses resource-config;
              list active-leases {
                description "Holds state for active client leases.";
                config false;
                key leased-prefix;
                leaf leased-prefix{
                  type inet:ipv6-prefix;
                }
                uses lease-information;
              }
            }
          }
        }
        uses message-stats;
      }
    }
  }

  /*
   * Notifications
   */

  notification address-pool-running-out {
    description "Notification sent when the address pool is going to
      run out. A threshold for utilization ratio of the pool has
      been defined in the server feature so that it will notify the
      administrator when the utilization ratio reaches the
      threshold, and such threshold is a settable parameter";
    leaf total-address-count {
      type uint64;
      mandatory true;
      description "Count of total addresses in the pool";
    }
    leaf max-address-count {
      type uint64;
      mandatory true;
      description "Maximum count of addresses that can be allocated
        in the pool. This value may be less than count of total
        addresses";
    }
    leaf allocated-address-count {
      type uint64;
      mandatory true;
      description "Count of allocated addresses in the pool";
    }
    leaf pool-id {
      type uint32;
      mandatory true;
      description "Pool ID";
    }
  }

  notification pd-pool-running-out {
    description "Notification sent when the address/prefix pool
      is going to run out. A threshold for utilization ratio
      of the pool has been defined in the server feature so that
      it will notify the administrator when the utilization ratio
      reaches the threshold, and such threshold is a settable
      parameter";
    leaf max-pd-space-utilization {
      type dhcpv6-common:threshold;
      mandatory true;
      description "Maximum PD space utilization";
    }
    leaf pd-space-utilization {
      type dhcpv6-common:threshold;
      mandatory true;
      description "Current PD space utilization";
    }
    leaf pool-id {
      type uint32;
      mandatory true;
      description "Pool ID";
    }
  }

  notification invalid-client-detected {
    description "Notification sent when the server has found a client
      which can be regarded as a potential attacker. Some description
      could also be included.";
    leaf duid {
      description "Client's DUID";
      type binary;
    }
    leaf description {
      type string;
      description "Description of the event";
    }
  }

  notification decline-received {
    description "Notification sent when the server has received
      DECLINE message from a client.";
    leaf duid {
      description "Client's DUID";
      type binary;
    }
    leaf-list addresses {
      type inet:ipv6-address;
      description "List of suspicious addresses";
    }
  }

  notification non-success-code-sent {
    description "Notification sent when the server responded
      to a client with non-success status code.";
    leaf status-code {
      type uint16;
      mandatory true;
      description "Status code returned to a client";
    }
    leaf duid {
      description "Client's DUID";
      type binary;
    }
  }
}
