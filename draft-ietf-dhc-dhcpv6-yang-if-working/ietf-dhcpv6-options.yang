module ietf-dhcpv6-options {
  yang-version 1.1;
  namespace "urn:ietf:params:xml:ns:yang:ietf-dhcpv6-options";
  prefix "dhcpv6-options";

  import ietf-inet-types {
    prefix inet;
  }
  import ietf-yang-types {
    prefix yang;
  }
  import ietf-dhcpv6-types {
    prefix dhcpv6-types;
  }

  organization "DHC WG";
  contact 
   "cuiyong@tsinghua.edu.cn
    wangh13@mails.tsinghua.edu.cn
    lh.sunlinh@gmail.com
    ian.farrer@telekom.de
    sladjana.zechlin@telekom.de
    hezihao9512@gmail.com";

  description "This model defines a YANG data module containing definitions
    of DHCPv6 options that can be used by DHCPv6 clients, relays and servers.";
  
  revision 2018-09-04 {
    description "";
    reference "I-D: draft-ietf-dhc-dhcpv6-yang";
  }

  revision 2018-03-04 {
    description "Resolved most issues on the DHC official
    github";
    reference "I-D: draft-ietf-dhc-dhcpv6-yang";
  }

  revision 2017-12-22 {
	  description "Resolve most issues on Ian's github.";
	  reference "I-D: draft-ietf-dhc-dhcpv6-yang";
  }
  
  revision 2017-11-24 {
    description "First version of the separated DHCPv6 options
      YANG model.";
    reference "I-D:draft-ietf-dhc-dhcpv6-yang";
  }

  /*
   * Features
   */
  
  //  features for server options
	feature server-unicast-op {
		description "Support for the Server Unicast option 
      OPTION_UNICAST (12)";
	}
	feature sip-server-domain-name-list-op {
		description "Support for the SIP Server Domain Name List option
      OPTION_SIP_SERVER_D (21)";
	}
	feature sip-server-address-list-op {
		description "Support for the SIP Server Address List option
      OPTION_SIP_SERVER_A (22)";
	}
  feature dns-servers-op {
    description "Support for the DNS Servers option
      OPTION_DNS_SERVERS (23)";
  }
	feature domain-searchlist-op {
		description "Support for the Domain Search List option
      OPTION_DOMAIN_LIST (24)";
	}
	feature nis-config-op {
		description "Support for the Network Information Service (NIS) Servers
      option OPTION_NIS_SERVERS (27)";
	}
	feature nis-plus-config-op {
		description "Support for the Network Information Service V2 (NIS+) 
			Servers option OPTION_NISP_SERVERS (28)";
	}
	feature nis-domain-name-op {
		description "Support for the Network Information Service (NIS)
			Domain Name option OPTION_NIS_DOMAIN_NAME (29)";
	}
	feature nis-plus-domain-name-op {
		description "Support for the Network Information Service V2 (NIS+)
			Server option OPTION_NISP_DOMAIN_NAME (30)";
	}
	feature sntp-server-op {
		description "Support for the Simple Network Protocol Configuration 
			(SNTP) Servers option OPTION_SNTP_SERVERS (31)";
	}
	feature info-refresh-time-op {
		description "Support for the Information Refresh Time option
      OPTION_INFORMATION_REFRESH_TIME (32)";
	}
  feature bcmcs-server-d-op {
    description "Support for the Broadcast and Multicast Service Controller
      Domain Name List Option for DHCPv6 OPTION_BCMCS_SERVER_D (33)";
  }
  feature bcmcs-server-a-op {
    description "Support for the Broadcast and Multicast Service Controller IPv6
      Address Option for DHCPv6 OPTION_BCMCS_SERVER_A (34)";
  }
  feature geoconf-civic-op {
    description "Support for the  Civic Addresses Configuration Information
      option OPTION_GEOCONF_CIVIC (36)";
  }
	feature client-fqdn-op {
		description "Support for the Client FQDN option
      OPTION_CLIENT_FQDN (39)";
	}
  feature pana-agent-op {
    description "Support for the PANA Authentication Agent DHCPv6 Option 
      OPTION_PANA_AGENT (40)";
  }
	feature posix-timezone-op {
		description "Support for the New POIX Timezone option
      OPTION_NEW_POSIX_TIMEZONE (41)";
	}
	feature tzdb-timezone-op {
		description "Support for the New TZDB Timezone option
      OPTION_NEW_TZDB_TIMEZONE (42)";
	}
	feature ntp-server-op {
		description "Support for the Network Time Protocol (NTP) Server option
      OPTION_NTP_SERVER (56)";
	}
	feature boot-file-url-op {
		description "Support for the Boot File URL option
      OPT_BOOTFILE_URL (59)";
	}
	feature boot-file-param-op {
		description "Support for the Boot File Parameters option
      OPT_BOOTFILE_PARAM (60)";
	}
	feature aftr-name-op {
		description "Support for the Address Family Transition Router (AFTR)
      option OPTION_AFTR_NAME (64)";
	}
	feature kbr-default-name-op {
		description "Support for the Kerberos Default Name option
      OPTION_KRB_DEFAULT_REALM_NAME (77)";
	}
	feature kbr-kdc-op {
		description "Support for the Kerberos KDC option
      OPTION_KRB_KDC (78)";
	}
	feature sol-max-rt-op {
		description "Support for the SOL_MAX_RT option
      OPTION_SOL_MAX_RT (82)";
	}
	feature inf-max-rt-op {
		description "Support for the INF_MAX_RT option
      OPTION_INF_MAX_RT (83)";
	}
	feature addr-selection-op {
		description "Support for Address Selection opiton
      OPTION_ADDRSEL (84)";
	}
	feature pcp-server-op {
		description "Support for the Port Control Protocol (PCP) option
      OPTION_V6_PCP_SERVER (86)";
	}
	feature s46-rule-op {
		description "Support for the S46 Rule option
      OPTION_S46_RULE (89)";
	}
	feature s46-br-op {
		description "Support for the S46 Border Relay (BR) option
      OPTION_S46_BR (90)";
	}
	feature s46-dmr-op {
		description "Support for the S46 Default Mapping Rule (DMR) option
      OPTION_S46_DMR (91)";
	}
	feature s46-v4-v6-binding-op {
		description "Support for the S46 IPv4/IPv6 Address Bind option
      OPTION_S46_V4V6BIND (92)";
	}

  // features for options which can be sent be either the server or the client
  feature rapid-commit-op {
		description "Support for the Rapid Commit option
      OPTION_RAPID_COMMIT (14)";
	}

	// features for relay-supplied options
  feature remote-id-op {
    description "Support for the Relay Agent Remote-ID option
      OPTION_REMOTE_ID (37)";
  }
  feature subscriber-id-op {
    description "Support for the Relay Agent Subscriber-ID option
      OPTION_SUBSCRIBER_ID (38)";
  }
  feature ero-op {
    description "Support for the DHCPv6 Relay Agent Echo Request option
      OPTION_ERO (43)";
  }
	feature erp-local-domain-name-op {
		description "Support for the ERP Local Domain Name option
      OPTION_ERP_LOCAL_DOMAIN_NAME (65)";
	}
	
	// features for client options
  feature mip6-hnidf-op {
    description "Support for the MIPv6 Home Network ID FQDN Option
      OPTION_MIP6_HNIDF (49)";
  }
	feature user-class-op {
		description "Support for the User Class option";
	}
	feature vendor-class-op {
		description "Support for Vendor Class option";
	}
	feature client-arch-type-op {
		description "Support for Client System Architecture
			Type option";
	}
	feature client-network-interface-identifier-op {
		description "Support for Client Network Interface
			Identifier option";
	}
	feature kbr-principal-name-op {
		description "Support for Kerberos Principal
			Name option";
	}
	feature kbr-realm-name-op {
		description "Support Kerberos Realm Name option";
	}
	feature client-link-layer-addr-op {
		description "Support for Client Link-Layer Address
			Option";
	}
	
	// features for custom options
	feature operator-op-ipv6-address {
		description "Support for Option with IPv6 Addresses";
	}
	feature operator-op-single-flag {
		description "Support for Option with Single Flag";
	}
	feature operator-op-ipv6-prefix {
		description "Support for Option with IPv6 Prefix";
	}
	feature operator-op-int32 {
		description "Support for Opion with 32-bit
			Integer Value";
	}
	feature operator-op-int16 {
		description "Support for Opion with 16-bit Integer Value";
	}
	feature operator-op-int8 {
		description "Support for Opion with 8-bit Integer Value";
	}
	feature operator-op-uri {
		description "Support for Opion with URI";
	}
	feature operator-op-textstring {
		description "Support for Opion with Text String";
	}
	feature operator-op-var-data {
		description "Support for Opion with Variable-Length Data";
	}
	feature operator-op-dns-wire {
		description "Support for Opion with DNS Wire
			Format Domain Name List";
	}
	
  /*
   * Groupings
   */
  
  grouping server-option-definitions {
    description "Contains definitions for options configured on the
      DHCPv6 server which will be supplied to clients.";

    uses server-client-option-definitions;
    uses server-relay-option-definitions;

    container server-unicast-option {
      if-feature server-unicast-op;
      presence "Enable this option";
      description "OPTION_UNICAST (12) Server Unicast Option";
      reference "RFC3315: Dynamic Host Configuration Protocol for 
        IPv6 (DHCPv6)";
      leaf server-address {
        type inet:ipv6-address;
        mandatory true;
        description "server ipv6 address";
      }
    }

    container sip-server-domain-name-list-option {
      if-feature sip-server-domain-name-list-op;
      presence "Enable this option";
      description "OPTION_SIP_SERVER_D (21) SIP Servers Domain Name List";
      reference "RFC3319: Dynamic Host Configuration Protocol
        (DHCPv6) Options for Session Initiation Protocol (SIP) Servers";
      list sip-server-domain-names {
        key sip-serv-domain-name-id;
        description "List of SIP server domain names";
        leaf sip-serv-domain-name-id {
          type uint8;
          mandatory true;
          description "SIP server domain list entry identifier";
        }
        leaf sip-serv-domain-name {
          type string;
          mandatory true;
          description "SIP server domain name list entry";
        }
      }
    }

    container sip-server-address-list-option {
      if-feature sip-server-address-list-op;
      presence "Enable this option";
      description "OPTION_SIP_SERVER_A (22) SIP Servers IPv6 Address List";
      reference "RFC3319: Dynamic Host Configuration Protocol (DHCPv6) 
        Options for Session Initiation Protocol (SIP) Servers";
      list sip-servers {
        key sip-serv-id;
        description "SIP server info";
        leaf sip-serv-id {
          type uint8;
          mandatory true;
          description "SIP server address list entry identifier";
        }
        leaf sip-serv-addr {
          type inet:ipv6-address;
          mandatory true;
          description "SIP server address list entry";
        }
      }
    }  

    container dns-servers-option {
      if-feature dns-servers-op;
      presence "Enable this option";
      description "OPTION_DNS_SERVERS (23) DNS recursive Name Server option";
      reference "RFC3646: DNS Configuration options for Dynamic Host Configuration 
        Protocol for IPv6 (DHCPv6)";
      list dns-server {
        key dns-serv-id;
        description "dns server info";
        leaf dns-serv-id {
          type uint8;
          mandatory true;
          description "DNS server list entry ID.";
        }
        leaf dns-serv-addr {
          type inet:ipv6-address;
          mandatory true;
          description "DNS server address.";
        }
      }
    } 

    container domain-searchlist-option {
      if-feature domain-searchlist-op;
      presence "Enable this option";
      description "OPTION_DOMAIN_LIST (24) Domain Search List Option";
      reference "RFC3646: DNS Configuration options for Dynamic
        Host Configuration Protocol for IPv6 (DHCPv6)";
      list domain-searchlist {
        key domain-searchlist-id;
        description "dns server info";
        leaf domain-searchlist-id {
          type uint8;
          mandatory true;
          description "Domain seachlist entry ID.";
        }
        leaf domain-search-list-entry {
          type string;
          mandatory true;
          description "Domain search list entry.";
        }
      }
    }

    container nis-config-option {
      if-feature nis-config-op;
      presence "Enable this option";
      description "OPTION_NIS_SERVERS (27) Network Information Service (NIS)
        Servers Option.";
      reference "RFC3898: Network Information Service (NIS) Configuration
        Options for Dynamic Host Configuration Protocol for IPv6 (DHCPv6)";
      list nis-server {
        key nis-serv-id;
        description "nis server info";
        leaf nis-serv-id {
          type uint8;
          mandatory true;
          description "nis server id";
        }
        leaf nis-serv-addr {
          type inet:ipv6-address;
          mandatory true;
          description "nis server addr";
        }
      }
    }

    container nis-plus-config-option {
      if-feature nis-plus-config-op;
      presence "Enable this option";
      description "OPTION_NISP_SERVERS (28): Network Information Service V2
        (NIS+) Servers Option.";
      reference "RFC3989: Network Information Service (NIS) Configuration
        Options for Dynamic Host Configuration Protocol for IPv6 (DHCPv6)";
      list nis-plus-server {
        key nis-plus-serv-id;
        description "NIS+ server information.";
        leaf nis-plus-serv-id {
          type uint8;
          mandatory true;
          description "nisp server id";
        }
        leaf nis-plus-serv-addr {
          type inet:ipv6-address;
          mandatory true;
          description "nisp server addr";
        }
      }
    }

    container nis-domain-name-option {
      if-feature nis-domain-name-op;
      presence "Enable this option";
      description "OPTION_NIS_DOMAIN_NAME (29) Network Information
        Service (NIS) Domain Name Option";
      reference "RFC3989: Network Information Service (NIS)
        Configuration Options for Dynamic Host Configuration Protocol
        for IPv6 (DHCPv6)";
      leaf nis-domain-name {
        type string;
        description "The Network Information Service (NIS) Domain Name
          option is used by the server to convey client's NIS Domain Name
          info to the client.";
      }
    }

    container nis-plus-domain-name-option {
      if-feature nis-plus-domain-name-op;
      presence "Enable this option";
      description "OPTION_NISP_DOMAIN_NAME (30) Network Information 
        Service V2 (NIS+) Domain Name Option";
      reference "RFC3989: Network Information Service (NIS)
        Configuration Options for Dynamic Host Configuration Protocol
        for IPv6 (DHCPv6)";
      leaf nis-plus-domain-name {
        type string;
        description "The Network Information Service V2 (NIS+) Domain Name
        option is used by the server to convey client's NIS+ Domain Name
        info to the client.";
      }
    } 

    container sntp-server-option {
      if-feature sntp-server-op;
      presence "Enable this option";
      description "OPTION_SNTP_SERVERS (31) Simple Network Time Protocol
        (SNTP) Servers Option";
      reference "RFC4075: Simple Network Time Protocol (SNTP) Configuration
        Option for DHCPv6";
      list sntp-server {
        key sntp-serv-id;
        description "sntp server info";
        leaf sntp-serv-id {
          type uint8;
          mandatory true;
          description "sntp server id";
        }
        leaf sntp-serv-addr {
          type inet:ipv6-address;
          mandatory true;
          description "sntp server addr";
        }
      }
    }

    container info-refresh-time-option {
      if-feature info-refresh-time-op;
      presence "Enable this option";	
      description "OPTION_INFORMATION_REFRESH_TIME (32) Information Refresh
        Time option.";
      reference "RFC4242: Information Refresh Time Option for Dynamic Host
        Configuration Protocol for IPv6 (DHCPv6";
      leaf info-refresh-time {
        type yang:timeticks;
        mandatory true;
        description "The refresh time.";
      }
    }

    container bcmcs-server-d {
      if-feature bcmcs-server-d-op;
      presence "Enable this option";
      description "OPTION_BCMCS_SERVER_D (33) Broadcast and Multicast Service
        Controller Domain Name List Option for DHCPv6";
      reference "RFC4280: Dynamic Host Configuration Protocol (DHCP) Options for
        Broadcast and Multicast Control Servers";
      list bcmcs-control-server-domain-names {
        leaf bcmcs-control-server-domain-name {
          description "Domain name of BCMCS control server.";
          type string;
          mandatory true;
  			}
      }
    }

    container bcmcs-server-a {
      if-feature bcmcs-server-a-op;
      presence "Enable this option";
      description "OPTION_BCMCS_SERVER_A (34) Broadcast and Multicast Service
        Controller IPv6 Address Option for DHCPv6";
      reference "RFC4280: Dynamic Host Configuration Protocol (DHCP) Options for
        Broadcast and Multicast Control Servers";
      list bcmcs-control-server-addressess {
        leaf bcmcs-control-server-address {
          description "IPv6 address of BCMCS control server.";
          type inet:ipv6-address;
          mandatory true;
  			}
      }
    }

    /* Option 35 is Unassigned */

    container geoconf-civic-option {
      if-feature geoconf-civic-op;
      presence "Enable this option";
      description "OPTION_GEOCONF_CIVIC (36) Civic Addresses Configuration
        Information option.";
      reference "Dynamic Host Configuration Protocol (DHCPv4 and DHCPv6) Option
          for Civic Addresses Configuration Information";
      leaf what {
        description "The 'what' element describes to which location the DHCP
          entry refers.  Currently, three options are defined: the location of
          the DHCP server (a value of 0), the location of the network element
          believed to be closest to the client (a value of 1), or the
          location of the client (a value of 2).  Option (2) SHOULD be used,
          but may not be known.  Options (0) and (1) SHOULD NOT be used
          unless it is known that the DHCP client is in close physical
          proximity to the server or network element.";
        mandatory true;
        type uint8 {
          range "0..2";
        }
      }
      leaf country-code {
        description "The two-letter ISO 3166 country code in capital ASCII
          letters, e.g., DE or US.  (Civic addresses always contain country
          designations, suggesting the use of a fixed-format field to save
          space.)";
        mandatory true;
        type string {
          length "2";
        }
      }
      list civic-address-elements {
        description "Zero or more elements comprising the civic and/or postal
          address.";
        leaf catype {
          description "A one-octet descriptor of the data civic address value.";
          type uint8;
        }
        leaf calength {
          description "The length, in octets, of the CAvalue, not including the
            CAlength field itself.";
          type uint8;
        }
        leaf cavalue {
          description "The civic address value";
          type string;
        }
      }
    }

    container pana-agent-option {
      if-feature pana-agent-op;
      presence "Enable this option";
      description "OPTION_PANA_AGENT (40) PANA Authentication Agent 
        DHCPv6 Option";
      reference "RFC5192: DHCP Options for Protocol for Carrying 
        Authentication for Network Access (PANA) Authentication Agents";
      leaf-list paa-ipv6-addresses {
        description "List of IPv6 PAA addresses for the client to use. The PAAs
          are listed in the order of preference for use by the client.";
        type inet:ipv6-address;
      }
    }

    container posix-timezone-option {
      if-feature posix-timezone-op;
      presence "Enable this option";
      description "OPTION_NEW_POSIX_TIMEZONE (41) Posix Timezone option";
      reference "RFC4833: Timezone Options for DHCP";
      leaf tz-posix {
        type string;
        mandatory true;
        description "TZ Posix IEEE 1003.1 String";
      }
    }

    container tzdb-timezone-option {
      if-feature tzdb-timezone-op;
      presence "Enable this option";
      description "OPTION_NEW_TZDB_TIMEZONE (42) Timezone Database option";
      reference "RFC4822: Timezone Options for DHCP";
      leaf tz-database {
        type string;
        mandatory true;
        description "Reference to the TZ Database";
      }
    }  

    /* Options 44, 45, 46, 47, and 48 are for the DHCPv6 lease query mechanism.
    (RFC5007) How (or if) this is modelled is a larger piece of work and the
    options definition needs to be tackled as part of this.
    */

    container ntp-server-option {
      //This option looks like it needs work to correctly model the
      //option as defined in the RFC.
    	
      // Zihao - Re-modelled so it only contains one time source suboption
      
      if-feature ntp-server-op;
      presence "Enable this option";
      description "OPTION_NTP_SERVER (56) NTP Server Option for DHCPv6";
      reference "RFC5908: Network Time Protocol (NTP) Server Option for
        DHCPv6";
      list ntp-server {
        key ntp-serv-id;
        description "ntp server info";
        leaf ntp-serv-id {
          type uint8;
          mandatory true;
          description "NTP server id";
        }
        choice ntp-time-source-suboption {
        	description "Select a NTP time source suboption.";
        	case server-address {
    	    	leaf-list ntp-serv-addr-suboption {
    	          type inet:ipv6-address;
    	          description "NTP server addr";
    	      }
      	  }
        	case server-multicast-address {
        		leaf-list ntp-serv-mul-addr-suboption {
              type inet:ipv6-address;
        	    description "NTP server multicast addr";
            }
        	}
        	case server-fqdn {
        		leaf-list ntp-serv-fqdn-suboption {
              type string;
              description "NTP server fqdn";
            }
        	}       	
        }
      }
    }

  	container boot-file-url-option {
  		if-feature boot-file-url-op;
  		presence "Enable this option";
  		description "OPT_BOOTFILE_URL (59) Boot File URL Option";
  		reference "RFC5970: DHCPv6 Options for Network Boot";		
  		list boot-file {
  			key boot-file-id;
  			description "boot file info";
  			leaf boot-file-id {
  				type uint8;
  				mandatory true;
  				description "boot file id";
  			}
        leaf-list suitable-arch-type {
          type uint16;
          description "architecture type";
        }
      	leaf-list suitable-net-if {
        	type uint32;
        	description "network interface";
      	}
  			leaf boot-file-url {
  				type string;
  				mandatory true;
  				description "url for boot file";
  			}
  		}
  	}

  	container boot-file-param-option {
  		if-feature boot-file-param-op;
  		presence "Enable this option";
  		description "OPT_BOOTFILE_PARAM (60) Boot File Parameters Option";
  		reference "RFC5970: DHCPv6 Options for Network Boot";
      list boot-file-paras {
        key para-id;
        description "boot file parameters";
        leaf para-id {
          type uint8;
          mandatory true;
          description "parameter id";
        }
        leaf parameter {
          type string;
          mandatory true;
          description "parameter value";
        }
      }
  	}

    container aftr-name-option {
      if-feature aftr-name-op;
      presence "Enable this option";
      description "OPTION_AFTR_NAME (64) AFTR-Name DHCPv6 Option";
      reference "RFC6334: Dynamic Host Configuration Protocol for IPv6
        (DHCPv6) Option for Dual-Stack Lite";
      leaf tunnel-endpoint-name {
        type string;
        mandatory true;
        description "aftr name";
      }
    }

    container kbr-default-name-option {
    	if-feature kbr-default-name-op;
    	presence "Enable this option";
    	description "OPTION_KRB_DEFAULT_REALM_NAME (77) Kerberos Default Realm Name Option";
    	reference "RFC6784: Kerberos Options for DHCPv6";
      leaf default-realm-name {
        type string;
        mandatory true;
        description "default realm name";
      }
    }

    container kbr-kdc-option {
    	if-feature kbr-kdc-op;
    	presence "Enable this option";
    	description "OPTION_KRB_KDC (78) Kerberos KDB Option";
    	reference "RFC6784: Kerberos Options for DHCPv6";
      list kdc-info {
        key kdc-id;
        description "kdc info";
        leaf kdc-id {
          type uint8;
          mandatory true;
          description "kdc id";
        }
        leaf priority {
          type uint16;
          mandatory true;
          description "priority";
        }
        leaf weight {
          type uint16;
          mandatory true;
          description "weight";
        }
        leaf transport-type {
          type uint8;
          mandatory true;
          description "transport type";
        }
        leaf port-number {
          type uint16;
          mandatory true;
          description "port number";
        }
        leaf kdc-ipv6-addr {
          type inet:ipv6-address;
          mandatory true;
          description "kdc ipv6 addr";
        }
        leaf realm-name {
          type string;
          mandatory true;
          description "realm name";
        }
      }
    }

    container sol-max-rt-option {
      if-feature sol-max-rt-op;
      presence "Enable this option";
      description "OPTION_SOL_MAX_RT (82) sol max rt option";
      reference "RFC7083: Modification to Default Values of
        SOL_MAX_RT and INF_MAX_RT";
        leaf sol-max-rt-value {
          type yang:timeticks;
          mandatory true;
          description "sol max rt value";
        }
    }

    container inf-max-rt-option {
      if-feature inf-max-rt-op;
      presence "Enable this option";
      description "OPTION_INF_MAX_RT (83) inf max rt option";
      reference "RFC7083: Modification to Default Values of
        SOL_MAX_RT and INF_MAX_RT";
      leaf inf-max-rt-value {
        type yang:timeticks;
        mandatory true;
        description "inf max rt value";
      }
    }

    container addr-selection-option {
      if-feature addr-selection-op;
      presence "Enable this option";
      description "OPTION_ADDRSEL (84) and OPTION_ADDRSEL_TABLE (85)";
      reference "RFC7078: Distributing Address Selection Policy Using
        DHCPv6";
      // if - Needs checking to see if this matches the RFC - there
      // are two options here.
      // Zihao - I think this matches RFC7078
      leaf a-bit-set {
        type boolean;
        mandatory true;
        description "a bit";
      }
      leaf p-bit-set {
        type boolean;
        mandatory true;
        description "p bit";
      }
      list policy-table {
        key policy-id;
        description "policy table";
        leaf policy-id {
          type uint8;
          mandatory true;
          description "policy id";
        }
        leaf label {
          type uint8;
          mandatory true;
          description "label";
        }
        leaf precedence {
          type uint8;
          mandatory true;
          description "precedence";
        }
        leaf prefix-len {
          type uint8;
          mandatory true;
          description "prefix length";
        }
        leaf prefix {
          type inet:ipv6-prefix;
          mandatory true;
          description "prefix";
        }
      }
    }

    container pcp-server-option {
      if-feature pcp-server-op;
      presence "Enable this option";
      description "OPTION_V6_PCP_SERVER (86) pcp server option";
      reference "RFC7291: DHCP Options for the Port Control
        Protocol (PCP)";
      list pcp-server {
        key pcp-serv-id;
        description "pcp server info";
        leaf pcp-serv-id {
          type uint8;
          mandatory true;
          description "pcp server id";
        }
        leaf pcp-serv-addr {
          type inet:ipv6-address;
          mandatory true;
          description "pcp server addr";
        }
      }
    }

    container s46-rule-option {
      if-feature s46-rule-op;
      presence "Enable this option";
      description "OPTION_S46_RULE (89) S46 rule option";
      reference "RFC7598: DHCPv6 Options for Configuration of
        Softwire Address and Port-Mapped Clients";
      list s46-rule {
        key rule-id;
        description "s46 rule";
        leaf rule-id {
          type uint8;
          mandatory true;
          description "rule id";
        }
        leaf rule-type {
          type enumeration {
            enum "BMR" {
              description "BMR";
            }
            enum "FMR" {
              description "FMR";
            }
          }
          mandatory true;
          description "rule type";
        }
        leaf prefix4-len {
          type uint8;
          mandatory true;
          description "ipv4 prefix length";
        }
        leaf ipv4-prefix {
          type inet:ipv4-prefix;
          mandatory true;
          description "ipv4 prefix";
        }
        leaf prefix6-len {
          type uint8;
          mandatory true;
          description "ipv6 prefix length";
        }
        leaf ipv6-prefix {
          type inet:ipv6-prefix;
          mandatory true;
          description "ipv6 prefix";
        }
        uses dhcpv6-types:portset-para;
      }
    }

    container s46-br-option {
      if-feature s46-br-op;
      presence "Enable this option";
      description "OPTION_S46_BR (90) S46 BR Option";
      reference "RFC7598: DHCPv6 Options for Configuration of
        Softwire Address and Port-Mapped Clients";
      list br {
        key br-id;
        description "br info";
        leaf br-id {
          type uint8;
          mandatory true;
          description "br id";
        }
        leaf br-ipv6-addr {
          type inet:ipv6-address;
          mandatory true;
          description "br ipv6 addr";
        }
      }
    }

    container s46-dmr-option {
      if-feature s46-dmr-op;
      presence "Enable this option";
      description "OPTION_S46_DMR (91) S46 DMR Option";
      reference "RFC7598: DHCPv6 Options for Configuration of
        Softwire Address and Port-Mapped Clients";
      list dmr {
        key dmr-id;
        description "dmr info";
        leaf dmr-id {
          type uint8;
          mandatory true;
          description "dmr id";
        }
        leaf dmr-prefix-len {
          type uint8;
          mandatory true;
          description "dmr prefix length";
        }
        leaf dmr-ipv6-prefix {
          type inet:ipv6-prefix;
          mandatory true;
          description "dmr ipv6 prefix";
        }
      }
    }

    container s46-v4-v6-binding-option {
      if-feature s46-v4-v6-binding-op;
      presence "Enable this option";
      description "OPTION_S46_V4V6BIND (92) S46 IPv4/IPv6 Address
        Binding option";
      reference "RFC7598: DHCPv6 Options for Configuration of
        Softwire Address and Port-Mapped Clients";
      list ce {
        key ce-id;
        description "ce info";
        leaf ce-id {
          type uint8;
          mandatory true;
          description "ce id";
        }
        leaf ipv4-addr {
          type inet:ipv4-address;
          mandatory true;
          description "ce ipv4 addr";
        }
        leaf bind-prefix6-len {
          type uint8;
          mandatory true;
          description "bind ipv6 prefix
            length";
        }
        leaf bind-ipv6-prefix {
          type inet:ipv6-address;
          mandatory true;
          description "bind ipv6 prefix";
        }
        uses dhcpv6-types:portset-para;
      }
    }
  }
  
  grouping server-client-option-definitions {
    description "Contains definitions for options which can be sent by either
      the DHCPv6 server or client.";
    
    container rapid-commit-option {
      if-feature rapid-commit-op;
      presence "Enable this option";
      description "OPTION_RAPID_COMMIT (14) Rapid Commit Option. The presence
        node is used to enable the option.";
      reference "RFC8415: Dynamic Host Configuration Protocol for IPv6 
        (DHCPv6)";
    }
    container client-fqdn-option {
      if-feature client-fqdn-op;
      presence "Enable this option";
      description "OPTION_CLIENT_FQDN (39) DHCPv6 Client FQDN Option";
      reference "RFC4704: The Dynamic Host Configuration Protocol for IPv6
        (DHCPv6) Client Fully Qualified Domain Name (FQDN) Option";
      leaf server-initiate-update {
        type boolean;
        mandatory true;
        description "server initiate";
      }
      leaf client-initiate-update {
        type boolean;
        mandatory true;
        description "client initiate";
      }
      leaf modify-name-from-cli {
        type boolean;
        mandatory true;
        description "modify by client";
      }
      leaf domain-name {
        description "The partial or fully qualified domain name"; 
        mandatory true;
        type string;
      }
    }
  }

  grouping server-relay-option-definitions {
    description "Contains definitions for options which can be sent by either
      the DHCPv6 relay or server.";
    container mip6-options {
      description "DHCP Options for Home Information Discovery in Mobile IPv6
        (MIPv6)";
      grouping mipv6-hn-prefix {
        description "OPTION_MIP6_HNP (71) MIPv6 Home Network Prefix Option";
        container mipv6-hn-prefix-option {
          leaf hn-prefix-len {
            description "Length of prefix";
            mandatory true;
            type uint8;
          }
          leaf hn-prefix {
            description "Home Network Prefix";
            mandatory true;
            type inet:ipv6-address;
          }
        }
      }
      grouping mipv6-hn-address {
        description "OPTION_MIP6_HAA (72) MIPv6 Home Agent Address Option";
        container mipv6-hn-prefix-option {
          leaf hn-address {
            description "IP Address of home agent";
            mandatory true;
            type inet:ipv6-address;
          }
        }
      }
      grouping mipv6-hn-haf {
        description "OPTION_MIP6_HAF (73) MIPv6 Home Agent FQDN Option";
        container mipv6-hn-haf-option {
          leaf hn-address {
            description "FQDN resolving to one or more IPv4 and/or IPv6
              addresses for the home agent.";
            mandatory true;
            type string;
          }
        }
      }
//      container mipv6-vdinf-option {
//        description "OPTION_MIP6_VDINF (50) MIPv6 Visited Home Network
//          Information Option";
//        list vdinf-options {
//          description "One or more options, specifying information about the
//            local ASP (visited domain).";
//          choice vdinf-option {
//            case hn-prefix {
//              uses :server-relay-option-definitions/mipv6-hn-prefix; // TODO: this causes error: bad argument value ":server-relay-option-definitions/mipv6-hn-prefix", should be of type identifier-ref
//            }
//          }
//        }
//      }
    }
/* Add RFC6610 options */
  }

  grouping relay-supplied-option-definitions {

    uses server-relay-option-definitions;

    container remote-id-option {
      if-feature remote-id-op;
      presence "Enable this option";
      description "OPTION_REMOTE_ID (37) The Relay Agent Remote-ID Option";
      reference "RFC4649: Dynamic Host Configuration Protocol for IPv6 (DHCPv6)
        Relay Agent Remote-ID Option";
      leaf enterprise-id {
        description "The vendor's registered Enterprise Number as registered
          with IANA";
        type uint32;
      }
      leaf remote-id {
        description "The opaque value for the remote-id.";
        type string;
      }
    }
    container subscriber-id-option {
      if-feature subscriber-id-op;
      presence "Enable this option";
      description "OPTION_SUBSCRIBER_ID (38) The Relay Agent Subscriber-ID
        Option";
      reference "RFC4580: Dynamic Host Configuration Protocol for IPv6 (DHCPv6)
        Relay Agent Subscriber-ID Option";
      leaf subscriber-id {
        description "The subscriber's identity.";
        type string;
      }
    }
    container ero-option {
      if-feature ero-op;
      presence "Enable this option";
      description "OPTION_ERO (43) The Relay Agent Echo Request Option";
      reference "RFC4994: DHCPv6 Relay Agent Echo Request Option";
      leaf-list requested-option-codes {
        description "The option code for an option requested by the relay
          agent.";
        type uint16;
      }
    }
 
    // if - The structure here needs to be checked and probably reworked.
    description "OPTION_RSOO (66) Relay-Supplied Options option";
    reference "RFC6422: Relay-Supplied DHCP Options";
    container erp-local-domain-name-option {
      if-feature erp-local-domain-name-op;
      presence "Enable this option";
      description "OPTION_ERP_LOCAL_DOMAIN_NAME (65) DHCPv6 ERP Local
        Domain Name Option";
      reference "RFC6440: The EAP Re-authentication Protocol (ERP)
        Local Domain Name DHCPv6 Option";
      list erp-for-client {
        key cli-id;
        description "erp for client";
        leaf cli-id {
          type uint32;
          mandatory true;
          description "client id";
        }
        container duid {
          description "Sets the DUID";
          // uses duid;
          // if - Maybe DUID definition needs to be moved to this module.
          uses dhcpv6-types:duid;
        }
        leaf erp-name {
          type string;
          mandatory true;
          description "erp name";
        }
      }
    }
  }

  grouping client-option-definitions {
    description "Contains definitions for options configured on the
      DHCPv6 client which will be sent to the server.";
    
    uses server-client-option-definitions;
    
    list new-or-standard-cli-option {
      key option-code;
      description "new or standard client option";
      leaf option-code {
        type uint16;
        mandatory true;
        description "option code";
      }
      leaf option-name {
        type string;
        mandatory true;
        description "option name";
      }
      leaf option-description {
        type string;
        mandatory true;
        description "description of client
          option";
      }
      leaf option-reference {
        type string;
        description "the reference of option";
      }
      leaf option-value {
        type string;
        mandatory true;
        description "the option value";
      }
    }

    container option-request-option {
      description "OPTION_ORO (6) Option Request Option. A client MUST include
        an Option Request option in a Solicit, Request, Renew, Rebind, or
        Information-request message to inform the server about options the
        client wants the server to send to the client.";
      reference "RFC3315: Dynamic Host Configuration Protocol for 
      IPv6 (DHCPv6)";
      list oro-option {
        key option-code;
        description "oro option";
        leaf option-code {
          type uint16;
          mandatory true;
          description "option code";
        }
        leaf description {
          type string;
          mandatory true;
          description "description of oro options";
        }
      }
    }

    container user-class-option {
      if-feature user-class-op;
      presence "Enable this option";
      description "OPTION_USER_CLASS (15) User Class Option";
      reference "RFC3315: Dynamic Host Configuration Protocol
        for IPv6 (DHCPv6)";
      list user-class {
        key user-class-id;
        description "user class";
        leaf user-class-id {
          type uint8;
          mandatory true;
          description "user class id";
        }
        leaf user-class-data {
          type string;
          mandatory true;
          description "The information contained in the data area
            of this option is contained in one or more opaque
            fields that represent the user class or classes of
            which the client is a member. ";
        }
      }
    }

    container vendor-class-option {
      if-feature vendor-class-op;
      presence "Enable this option";
      description "OPTION_VENDOR_CLASS (16) Vendor Class Option";
      reference "RFC3315: Dynamic Host Configuration Protocol
        for IPv6 (DHCPv6)";
      leaf enterprise-number {
        type uint32;
        mandatory true;
        description "enterprise number";
      }     
      list vendor-class {
    	  key vendor-class-id;
    	  description "vendor class";
        leaf vendor-class-id {
          type uint8;
          mandatory true;
          description "vendor class id";
        }
        leaf vendor-class-data {
      	  type string;
      	  mandatory true;
      	  description "The vendor-class-data is composed of a series of 
            separate items, each of which describes some characteristic 
            of the client's hardware configuration. Examples of 
            vendor-class-data instances might include the version of the 
            operating system the client is running or the amount of memory 
            installed on the client.";
        }
      }
    }


    container mip6-hnidf-option {
      if-feature mip6-hnidf-op;
      presence "Enable this option";
      description "OPTION_MIP6_HNIDF (49) MIPv6 Home Network ID FQDN Option";
      reference "RFC6610: DHCP Options for Home Information Discovery in Mobile
        IPv6 (MIPv6)";
      leaf home-net-id-fqdn {
        description "A Fully Qualified Domain Name (FQDN) that identifies a
          mobile IP home network for which the client is seeking configuration
          information.";
        type string;
      }
    }

    container client-arch-type-option {
      if-feature client-arch-type-op;
      presence "Enable this option";
      description "OPTION_CLIENT_ARCH_TYPE (61) Client System
        Architecture Type Option";
      reference "RFC5970: DHCPv6 Options for Network Boot";
      list architecture-types {
        key type-id;
        description "architecture types";
        leaf type-id {
          type uint16;
          mandatory true;
          description "type id";
        }
        leaf most-preferred {
          type boolean;
          mandatory true;
          description "most preferred flag";
        }
      }
    }

    container client-network-interface-identifier-option {
      if-feature client-network-interface-identifier-op;
      presence "Enable this option";
      description "OPTION_NII (62) Client Network Interface 
    	  Identifier Option";
      reference "RFC5970: DHCPv6 Options for Network Boot";
      leaf type {
        type uint8;
        mandatory true;
        description "type";
      }
      leaf major {
        type uint8;
        mandatory true;
        description "major";
      }
      leaf minor {
        type uint8;
        mandatory true;
        description "minor";
      }
    }

    container kbr-principal-name-option {
      if-feature kbr-principal-name-op;
      presence "Enable this option";
      description "OPTION_KRB_PRINCIPAL_NAME (75) Kerberos
        Principal Name Option";
      reference "RFC6784: Kerberos Options for DHCPv6";
      list principle-name {
    	  key principle-name-id;
    	  description "principle name";
    	  leaf principle-name-id {
    		  type uint8;
    		  mandatory true;
    		  description "principle name id";
    	  }
    	  leaf name-type {
    		  type int32;
    		  mandatory true;
    		  description "This field specifies the type of name that follows.";
    	  }
    	  leaf name-string {
    		  type string;
    		  mandatory true;
    		  description "This field encodes a sequence of components that form
    			  a name, each component encoded as a KerberoString";
    	  }
      }
    }

    container kbr-realm-name-option {
    	if-feature kbr-realm-name-op;
    	presence "Enable this option";
    	description "OPTION_KRB_REALM_NAME (76) Kerberos Realm Name Option";
    	reference "RFC6784: Kerberos Options for DHCPv6";
    	leaf realm-name {
    		type string;
    		mandatory true;
    		description "realm name";
    	}
    }

    container client-link-layer-addr-option {
      if-feature client-link-layer-addr-op;
      presence "Enable this option";
      description "OPTION_CLIENT_LINKLAYER_ADDR (79) DHCPv6 Client
        Link-Layer Address Option";
      reference "RFC6939: Client Link-Layer Address Option in
        DHCPv6";
      leaf link-layer-type {
        type uint16;
        mandatory true;
        description "Client link-layer address type. The link-layer
          type MUST be a valid hardware type assigned by the IANA,
          as described in [RFC0826]";
      }
      leaf link-layer-addr {
        type string;
        mandatory true;
        description "Client link-layer address";
      }
    }

  }

  
  grouping custom-option-definitions {
    description "operator customized options";

    container operator-option-ipv6-address {
      if-feature operator-op-ipv6-address;
      presence "Enable this option";
      description "operator ipv6 address option";
      reference "RFC7227: Guidelines for Creating New DHCPv6 Options";
      leaf option-code {
        description "Operator defined DHCPv6 option code allocated
          for this option.";
        type uint16;
      }
      list operator-ipv6-addr {
        key operator-ipv6-addr-id;
        description "operator ipv6 address info";
        leaf operator-ipv6-addr-id {
          type uint8;
          mandatory true;
          description "operator ipv6 address id";
        }
        leaf operator-ipv6-addr {
          type inet:ipv6-address;
          mandatory true;
          description "operator ipv6 address id";
        }
      }
    }

    container operator-option-single-flag {
      if-feature operator-op-single-flag;
      presence "Enable this option";
      description "Operator defined single flag option. The presence node is 
        used to enable the option.";
      reference "RFC7227: Guidelines for Creating New DHCPv6 Options";
      leaf option-code {
        description "Operator defined DHCPv6 option code allocated
          for this option.";
        type uint16;
      }
    }

    container operator-option-ipv6-prefix {
      if-feature operator-op-ipv6-prefix;
      presence "Enable this option";
      description "Operator defined ipv6 prefix option";
      reference "RFC7227: Guidelines for Creating New DHCPv6
        Options";
      leaf option-code {
        description "Operator defined DHCPv6 option code allocated
          for this option.";
        type uint16;
      }
      list operator-ipv6-prefix {
        key operator-ipv6-prefix-id;
        description "operator ipv6 prefix info";
        leaf operator-ipv6-prefix-id {
          type uint8;
          mandatory true;
          description "operator ipv6 prefix id";
        }
        leaf operator-ipv6-prefix6-len {
          type uint8;
          mandatory true;
          description "operator ipv6 prefix length";
        }
        leaf operator-ipv6-prefix {
          type inet:ipv6-prefix;
          mandatory true;
          description "operator ipv6 prefix";
        }
      }
    }

    container operator-option-int32 {
      if-feature operator-op-int32;
      presence "Enable this option";
      description "operator integer 32 option";
      reference "RFC7227: Guidelines for Creating New DHCPv6
        Options";
      leaf option-code {
        description "Operator defined DHCPv6 option code allocated
          for this option.";
        type uint16;
      }
      list int32val {
        key int32val-id;
        description "operator integer 32 info";
        leaf int32val-id {
          type uint8;
          mandatory true;
          description "operator integer 32 id";
        }
        leaf int32val {
          type uint32;
          mandatory true;
          description "operator integer 32 value";
        }
      }
    }

    container operator-option-int16 {
      if-feature operator-op-int16;
      presence "Enable this option";
      description "operator integer 16 option";
      reference "RFC7227: Guidelines for Creating New DHCPv6
        Options";
      leaf option-code {
        description "Operator defined DHCPv6 option code allocated
          for this option.";
        type uint16;
      }
      list int16val {
        key int16val-id;
        description "operator integer 16 info";
        leaf int16val-id {
          type uint8;
          mandatory true;
          description "operator integer 16 id";
        }
        leaf int16val {
          type uint16;
          mandatory true;
          description "operator integer 16 value";
        }
      }
    }

    container operator-option-int8 {
      if-feature operator-op-int8;
      presence "Enable this option";
      description "operator integer 8 option";
      reference "RFC7227: Guidelines for Creating New DHCPv6
        Options";
      leaf option-code {
        description "Operator defined DHCPv6 option code allocated
          for this option.";
        type uint16;
      }
      list int8val {
        key int8val-id;
        description "operator integer 8 info";
        leaf int8val-id {
          type uint8;
          mandatory true;
          description "operator integer 8 id";
        }
        leaf int8val {
          type uint8;
          mandatory true;
          description "operator integer 8 value";
        }
      }
    }

    container operator-option-uri {
      if-feature operator-op-uri;
      presence "Enable this option";
      description "operator uri option";
      reference "RFC7227: Guidelines for Creating New DHCPv6 Options";
      leaf option-code {
        description "Operator defined DHCPv6 option code allocated
          for this option.";
        type uint16;
      }
      list uri{
        key uri-id;
        description "operator uri info";
        leaf uri-id {
          type uint8;
          mandatory true;
          description "operator uri id";
        }
        leaf uri {
          type string;
          mandatory true;
          description "operator uri value";
        }
      }
    }

    container operator-option-textstring {
      if-feature operator-op-textstring;
      presence "Enable this option";
      description "operator itext string option";
      reference "RFC7227: Guidelines for Creating New DHCPv6 Options";
      leaf option-code {
        description "Operator defined DHCPv6 option code allocated
          for this option.";
        type uint16;
      }
      list textstring{
        key textstring-id;
        description "operator text string info";
        leaf textstring-id {
          type uint8;
          mandatory true;
          description "operator text string id";
        }
        leaf textstring {
          type string;
          mandatory true;
          description "operator text string value";
        }
      }
    }

    container operator-option-var-data {
      if-feature operator-op-var-data;
      presence "Enable this option";
      description "operator variable length data option";
      reference "RFC7227: Guidelines for Creating New DHCPv6 Options";
      leaf option-code {
        description "Operator defined DHCPv6 option code allocated
          for this option.";
        type uint16;
      }
      list int32val {
        key var-data-id;
        description "Operator ivariable length data info";
        leaf var-data-id {
          type uint8;
          mandatory true;
          description "Operator variable length id";
        }
        leaf var-data {
          type binary;
          mandatory true;
          description "Operator variable length value";
        }
      }
    }

    container operator-option-dns-wire {
      if-feature operator-op-dns-wire;
      presence "Enable this option";
      description "Operator DNS wire format domain name list option.";
      reference "RFC7227: Guidelines for Creating New DHCPv6
        Options";
      leaf option-code {
        description "Operator defined DHCPv6 option code allocated
          for this option.";
        type uint16;
      }
      list operator-option-dns-wires {
        key operator-option-dns-wire-id;
        description "Operator DNS wire format info";
        leaf operator-option-dns-wire-id {
          type uint8;
          mandatory true;
          description "Operator DNS wire format id";
        }
        leaf operator-option-dns-wire {
          type binary;
          mandatory true;
          description "Operator DNS wire format value.";
        }
      }
    } 
  }
}
