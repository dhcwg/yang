module ietf-dhcpv6-options-rfc4833-server {
  yang-version 1.1;
  namespace "urn:ietf:params:xml:ns:yang:ietf-dhcpv6-options-rfc4833-server";
  prefix "rfc4833-srv";

  import ietf-inet-types {
    prefix inet;
  }

  import ietf-dhcpv6-server {
    prefix dhcpv6-server;
  }

  organization "DHC WG";
  contact
    "ian.farrer@telekom.de";

  description "This YANG module contains DHCPv6 options defined
    in RFC3319 that can be used by DHCPv6 servers.

    Copyright (c) 2018 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC 8513; see
    the RFC itself for full legal notices.";

  revision 2020-02-21 {
    description "Initial version.";
    reference "I-D: draft-ietf-dhc-dhcpv6-yang";
  }

  /*
   * Groupings
   */

  grouping posix-timezone-option {
    container posix-timezone-option {
      description "OPTION_NEW_POSIX_TIMEZONE (41) Posix Timezone option";
      reference "RFC4833: Timezone Options for DHCP";
      leaf tz-posix {
        type string;
        description "TZ Posix IEEE 1003.1 String";
      }
    }
  }

  grouping tzdb-timezone-option {
    container tzdb-timezone-option {
      description "OPTION_NEW_TZDB_TIMEZONE (42) Timezone Database option";
      reference "RFC4833: Timezone Options for DHCP";
      leaf tz-database {
        type string;
        description "Reference to the TZ Database";
      }
    }
  }

  augment "/dhcpv6-server:dhcpv6-server/dhcpv6-server:option-sets/dhcpv6-server:option-set" {
    when "../../../dhcpv6-server:dhcpv6-node-type='dhcpv6-server:server'";
    description "Augment the option definition groupings to the
      server module.";
    uses tzdb-timezone-option;
    uses posix-timezone-option;
  }
}
