module ietf-dhcpv6-options-rfc3646-server {
  yang-version 1.1;
  namespace "urn:ietf:params:xml:ns:yang:" + 
    "ietf-dhcpv6-options-rfc3646-server";
  prefix "rfc3646-srv";

  import ietf-inet-types {
    prefix inet;
  }

  import ietf-dhcpv6-server {
    prefix dhcpv6-server;
  }

  organization "DHC WG";
  contact
    "ian.farrer@telekom.de";

  description "This YANG module contains DHCPv6 options defined
    in RFC3319 that can be used by DHCPv6 servers.

    Copyright (c) 2018 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC 8513; see
    the RFC itself for full legal notices.";

  revision 2020-02-21 {
    description "Initial version.";
    reference "I-D: draft-ietf-dhc-dhcpv6-yang";
  }

  /*
   * Groupings
   */

  grouping dns-servers-option-group {
    description "OPTION_DNS_SERVERS (23) DNS recursive Name Server
      option";
    reference "RFC3646: DNS Configuration options for Dynamic Host
      Configuration Protocol for IPv6 (DHCPv6)";
    container dns-servers-option {
      description "OPTION_DNS_SERVERS (23) DNS recursive Name Server
        option container.";
      list dns-server {
        key dns-serv-id;
        description "List of DNS server addresses.";
        leaf dns-serv-id {
          type uint8;
          description "DNS server list entry ID.";
        }
        leaf dns-serv-addr {
          type inet:ipv6-address;
          description "DNS server address.";
        }
      }
    }
  }

  grouping domain-searchlist-option-group {
    description "OPTION_DOMAIN_LIST (24) Domain Search List Option";
    reference "RFC3646: DNS Configuration options for Dynamic
      Host Configuration Protocol for IPv6 (DHCPv6)";
    container domain-searchlist-option {
      description "OPTION_DOMAIN_LIST (24) Domain Search List Option
        container.";    
      list domain-searchlist {
        key domain-searchlist-id;
        description "List of DNS search domains.";
        leaf domain-searchlist-id {
          type uint8;
          description "Domain seachlist entry ID.";
        }
        leaf domain-search-list-entry {
          type string;
          description "Domain search list entry.";
        }
      }
    }
  }

  augment "/dhcpv6-server:dhcpv6-server/dhcpv6-server:option-sets/" + 
    "dhcpv6-server:option-set" {
    when "../../../dhcpv6-server:dhcpv6-node-type=" + 
      "'dhcpv6-server:server'";
    description "Augment the option definition groupings to the
      server module.";
    uses dns-servers-option-group; 
    uses domain-searchlist-option-group;
  }
}
