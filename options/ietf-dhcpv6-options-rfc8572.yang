module ietf-dhcpv6-options-rfc8572 {
  yang-version 1.1;
  namespace "urn:ietf:params:xml:ns:yang:ietf-dhcpv6-options-rfc8572";
  prefix "rfc8572";

 import ietf-dhcpv6-server {
    prefix dhcpv6-server;
  }

  organization
    "IETF DHC (Dynamic Host Configuration) Working Group";

  contact
    "WG Web:   <http://datatracker.ietf.org/wg/dhc/>
    WG List:  <mailto:dhcwg@ietf.org>
    Author:   Ian Farrer <ian.farrer@telekom.de>";

    description "This YANG module contains DHCPv6 options defined
      in RFC 7598 that can be used by DHCPv6 servers.

      Copyright (c) 2021 IETF Trust and the persons identified as
      authors of the code.  All rights reserved.

      Redistribution and use in source and binary forms, with or
      without modification, is permitted pursuant to, and subject
      to the license terms contained in, the Simplified BSD License
      set forth in Section 4.c of the IETF Trust's Legal Provisions
      Relating to IETF Documents
      (http://trustee.ietf.org/license-info).

      This version of this YANG module is part of RFC XXXX; see
      the RFC itself for full legal notices.";

  revision 2021-04-27 {
    description "Initial version.";
    reference "I-D: draft-ietf-dhc-dhcpv6-yang";
  }

  revision 2020-02-21 {
    description "Initial version.";
    reference "I-D: draft-ietf-dhc-dhcpv6-yang";
  }

  /*
   * Groupings
   */

  grouping pd-exclude-option-group {
    container bootstrap-server-list {
      if-feature dhcpv6-server:prefix-delegation;
      description "OPTION_V6_SZTP_REDIRECT (136) DHCPv6 SZTP Redirect Option.";
      reference "RFC8572: Secure Zero Touch Provisioning (SZTP)";
      leaflist bootstrap-server {
        description "The IPv6 Subnet ID and prefix-len that the
          delegating router includes in the OPTION_PD_EXCLUDE
          option that is excluded from the delegated prefix set.";
        type inet:uri;
      }
    }
  }

  augment "/dhcpv6-server:dhcpv6-server/dhcpv6-server:option-sets/" +
    "dhcpv6-server:option-set" {
    description "Augment the option definition groupings to the
      server module.";
    uses pd-exclude-option-group;
  }
}
