module ietf-dhcpv6-options-rfcXXXX {
  yang-version 1.1;
  namespace "urn:ietf:params:xml:ns:yang:ietf-dhcpv6-options-rfcXXXX";
  prefix "rfcXXXX";

  import ietf-inet-types {
    prefix inet;
  }

  import ietf-dhcpv6-server {
    prefix dhcpv6-server;
  }

  organization "DHC WG";
  contact
    "ian.farrer@telekom.de";

  description "This YANG module contains DHCPv6 options defined
    in RFCXXXX that can be used by DHCPv6 servers.";

  revision 2020-02-21 {
    description "Initial version.";
    reference "I-D: draft-ietf-dhc-dhcpv6-yang";
  }

  /*
   * Groupings
   */
  grouping xxxx-option-group {
    container xxxx-option {
    }
  }


  augment "/dhcpv6-server:dhcpv6-server/dhcpv6-server:option-sets/" +
    "dhcpv6-server:option-set" {
    description "Augment the option definition groupings to the
      server module.";
    uses xxxx-option-group;
  }
}
