module ietf-dhcpv6-options-rfc8415-relay {
  yang-version 1.1;
  namespace "urn:ietf:params:xml:ns:yang:" + 
    "ietf-dhcpv6-options-rfc8415-relay";
  prefix "rfc8415-rly";

  import ietf-dhcpv6-relay {
    prefix dhcpv6-relay;
    reference
      "To be updated on publication";
  }

  organization "DHC WG";
  contact
    "cuiyong@tsinghua.edu.cn
    wangh13@mails.tsinghua.edu.cn
    lh.sunlinh@gmail.com
    ian.farrer@telekom.de
    sladjana.zechlin@telekom.de
    hezihao9512@gmail.com";

  description "This YANG module contains DHCPv6 options defined
    in RFC8415 that can be used by DHCPv6 clients.

    Copyright (c) 2021 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX
    (https://www.rfc-editor.org/info/rfcXXXX); see the RFC itself
    for full legal notices.
  
    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  revision 2021-01-06 {
    description "Version update for draft -16 publication.";
    reference "I-D: draft-ietf-dhc-dhcpv6-yang-16";
  }

  revision 2020-12-22 {
    description "Version update for draft -13 publication.";
    reference "I-D: draft-ietf-dhc-dhcpv6-yang-15";
  }

  revision 2020-12-10 {
    description "Version update for draft -13 publication.";
    reference "I-D: draft-ietf-dhc-dhcpv6-yang-13";
  }

  revision 2020-12-01 {
    description "Version update for draft -12 publication.";
    reference "I-D: draft-ietf-dhc-dhcpv6-yang-12";
  }

  revision 2020-11-19 {
    description "Separated into a relay specific set of options.";
    reference "I-D: draft-ietf-dhc-dhcpv6-yang-12";
  }

  revision 2020-05-26 {
    description "Version update for draft -11 publication and
      to align revisions across the different modules.";
    reference "I-D: draft-ietf-dhc-dhcpv6-yang-11";
  }

  revision 2019-06-07 {
    description "Major reworking to only contain RFC8415 options.
      if-feature for each option removed. Removed groupings
      of features by device or combination of devices. Added ";
    reference "I-D: draft-ietf-dhc-dhcpv6-yang";
  }

  revision 2018-09-04 {
    description "";
    reference "I-D: draft-ietf-dhc-dhcpv6-yang";
  }

  revision 2018-03-04 {
    description "Resolved most issues on the DHC official
      github";
    reference "I-D: draft-ietf-dhc-dhcpv6-yang";
  }

  revision 2017-12-22 {
    description "Resolve most issues on Ian's github.";
    reference "I-D: draft-ietf-dhc-dhcpv6-yang";
  }

  revision 2017-11-24 {
    description "First version of the separated DHCPv6 options
      YANG model.";
    reference "I-D:draft-ietf-dhc-dhcpv6-yang";
  }

  /*
   * Groupings
   */

  grouping auth-option-group {
    description "OPTION_AUTH (11) Authentication Option.";
    reference "RFC8415: Dynamic Host Configuration Protocol
        for IPv6 (DHCPv6)";   
    container auth-option {
      description "OPTION_AUTH (11) Authentication Option 
        container.";
      leaf protocol {
        type uint8;
        description "The authentication protocol used in this
          Authentication option.";
      }
      leaf algorithm {
        type uint8;
        description "The algorithm used in the authentication
          protocol.";
      }
      leaf rdm {
        type uint8;
        description "The replay detection method used
          in this Authentication option.";
      }
      leaf replay-detection {
        type uint64;
        description "The replay detection information for the RDM.";
      }
      leaf auth-information {
        type string;
        description "The authentication information, as specified
          by the protocol and algorithm used in this Authentication
          option.";
      }
    }
  }

  grouping status-code-option-group {
    description "OPTION_STATUS_CODE (13) Status Code Option.";
    reference "RFC8415: Dynamic Host Configuration Protocol
      for IPv6 (DHCPv6)";   
    container status-code-option {
      description "OPTION_STATUS_CODE (13) Status Code Option 
        container.";
      leaf status-code {
        type uint16;
        description "The numeric code for the status encoded
          in this option. See the Status Codes registry at
          <https://www.iana.org/assignments/dhcpv6-parameters>
          for the current list of status codes.";
      }
      leaf status-message {
        type string;
        description "A UTF-8 encoded text string suitable for
          display to an end user. MUST NOT be null-terminated.";
      }
    }
  }

  grouping interface-id-option-group {
    description "OPTION_INTERFACE_ID (18) Interface-Id Option.";
    reference "RFC8415: Dynamic Host Configuration Protocol for
        IPv6 (DHCPv6)";
    container interface-id-option {
     description "OPTION_INTERFACE_ID (18) Interface-Id Option
       container.";
     leaf interface-id {
        type string;
        description "An opaque value of arbitrary length generated
          by the relay agent to identify one of the relay agent's
          interfaces.";
      }
    }
  }

  /*
   * Augmentations
   */

  augment "/dhcpv6-relay:dhcpv6-relay/dhcpv6-relay:relay-if/" + 
    "dhcpv6-relay:relay-options" {
    when "../../../dhcpv6-relay:dhcpv6-node-type=" + 
      "'dhcpv6-relay:relay'";
    description "Augment the option definition groupings to the
      relay module.";
    uses auth-option-group;
    uses status-code-option-group;
    uses interface-id-option-group;
  }
}
